;;; FILE SINH TỰ ĐỘNG từ vk_nguon.lsp bằng scripts\gop_vk.py — KHÔNG SỬA TAY.
;;; Chữ có dấu trong chuỗi đã đổi thành mã \U+XXXX để hiện đúng với cả LISPSYS = 0 và 1.
;;; VK.lsp — Chia đố thanh đứng và dựng vách kính mặt bằng (Archivina)
;;; Lệnh: VK
;;;   Bảng hỏi: chiều dài vách, cửa sổ mở / cửa đi (số lượng, bề rộng tâm-tâm, ô đặt cửa).
;;;   Bảng tự cập nhật số đố và khoảng cách các đố; OK -> chọn điểm đầu vách (mép ngoài) và hướng vách.
;;;   Bảng hiện trước; chưa có chiều dài thì bấm "Pick 2 điểm <": chọn điểm đầu + điểm cuối vách trên mặt bằng,
;;;   bảng mở lại với chiều dài đã điền -> chọn cửa sổ / cửa đi -> OK dựng vách đúng 2 điểm đó (người dùng chốt
;;;   29/10/2026). Sửa tay chiều dài sau khi pick thì OK hỏi điểm như cũ.
;;; Quy tắc chia (người dùng chốt 28/10/2026):
;;;   - Đố rộng 65: tâm đố đầu / cuối cách mép ngoài 32,5; khoảng chia S = L - 65.
;;;   - Trừ bề rộng tâm-tâm các cửa, phần còn lại chia ĐỀU thành N ô kính, N nhỏ nhất để mỗi ô < 1200.
;;;     Không làm tròn khoảng chia.
;;;   - Cửa đặt vào ô thứ k (đếm từ trái, kể cả ô cửa); bỏ trống thì tự rải đều (1 cửa -> ô giữa).
;;; Kết quả: block "VACH KINH <dài>" trên layer A-Window gồm block đố VK_DoDung, cửa VK_CuaSoMo / VK_CuaDi
;;;   (bề rộng khác mặc định -> block kéo giãn VK_CuaSoMo_<rộng> / VK_CuaDi_<rộng>), kính ô cố định, và
;;;   2 hàng kích thước kiểm tra (chuỗi đố + tổng) kiểu "dim cua", layer Defpoints, nằm trong block.
;;; Block VK_*, kiểu dim "dim cua" nhúng sẵn trong file (cuối file): chép 1 file VK.lsp sang máy khác là dùng được.
;;; Yêu cầu: AutoCAD 2021+. Chữ có dấu trong chuỗi đã đổi sang \U+XXXX nên chạy được cả LISPSYS = 0 và 1. Không xoá, không sửa đối tượng có sẵn trong bản vẽ.

(vl-load-com)

;;; ---------------------------------------------------------------- thông số
;;;   vk:do-rong: bề rộng đố dùng để chia; vk:toi-da: khoảng tâm-tâm phải nhỏ hơn
;;;   vk:nua-do: nửa bề rộng đố trong block (65,74 / 2), vùng không kéo giãn khi đổi rộng cửa
;;;   vk:so-goc / vk:di-goc: tâm-tâm 2 đố của block VK_CuaSoMo / VK_CuaDi
;;;   vk:kinh: 2 tấm kính ô cố định (y so với trục vách), theo kính lá cửa sổ
;;;   vk:dim-chuoi / vk:dim-tong: đường dim chuỗi đố / dim tổng cách trục vách
(setq vk:do-rong 65.0
      vk:toi-da 1200.0
      vk:nua-do 32.87
      vk:so-goc 1000.0
      vk:di-goc 1665.0
      vk:kinh '((42.04 48.04) (56.86 62.86))
      vk:dim-chuoi 165.0
      vk:dim-tong 260.0
      vk:layer "A-Window"
      vk:layer-dim "Defpoints"
      vk:dimstyle "dim cua")

;;; ---------------------------------------------------------------- tiện ích
(defun vk:undo-ok () (= 1 (logand 3 (getvar "UNDOCTL"))))

;;; Số -> chuỗi gọn, dấu thập phân là dấu phẩy: 1058.75 -> "1058,75", 1000.0 -> "1000"
(defun vk:so (x / s)
  (setq s (rtos x 2 2))
  (if (vl-string-search "." s)
    (setq s (vl-string-right-trim "." (vl-string-right-trim "0" s))))
  (vl-string-subst "," "." s)
)

;;; Chuỗi -> số thực (nhận cả dấu phẩy thập phân); rỗng / sai -> nil
(defun vk:doc-so (s)
  (if (and s (/= (vl-string-trim " " s) ""))
    (distof (vl-string-subst "." "," (vl-string-trim " " s)) 2))
)

;;; "1, 3;5" -> (1 3 5); rỗng hoặc chỉ toàn 0 -> nil (tự đặt); số 0 bị bỏ qua (người dùng nhập 0 = tự đặt,
;;; báo 28/10/2026); chữ / số âm -> 'LOI
(defun vk:doc-vt (s / ds tu c kq)
  (setq s (vl-string-trim " " (if s s "")))
  (if (= s "")
    nil
    (progn
      (foreach c (vl-string->list s)
        ;; 44 = dấu phẩy, 59 = chấm phẩy, 32 = dấu cách
        (if (member c '(44 59 32))
          (progn (if tu (setq ds (cons tu ds))) (setq tu nil))
          (setq tu (strcat (if tu tu "") (chr c)))))
      (if tu (setq ds (cons tu ds)))
      (setq kq (mapcar '(lambda (x) (if (wcmatch x "#,##,###") (atoi x) -1)) (reverse ds)))
      (cond
        ((vl-some '(lambda (x) (< x 0)) kq) 'LOI)
        (T (vl-remove 0 kq)))
    )
  )
)

(defun vk:lap (n x / kq) (repeat n (setq kq (cons x kq))) kq)

;;; ---------------------------------------------------------------- tính chia đố
;;; L: dài vách; ns / nd: số cửa sổ / cửa đi; ws / wd: tâm-tâm cửa; vs / vd: danh sách ô hoặc nil (tự rải)
;;; Trả về (o tam b n): o = ((loai rong) ...) loai "K" kính / "S" cửa sổ / "D" cửa đi; tam = vị trí tâm đố;
;;; b = rộng ô kính; n = số ô kính. Lỗi -> chuỗi thông báo.
(defun vk:chia (L ns ws nd wd vs vd / S R n tong co-dinh tu-do tu-dong o b tam i k x)
  (cond
    ((or (not L) (<= L vk:do-rong)) "Nh\\U+1EADp chi\\U+1EC1u d\\U+00E0i v\\U+00E1ch l\\U+1EDBn h\\U+01A1n 65 mm")
    ((or (< ns 0) (< nd 0)) "S\\U+1ED1 l\\U+01B0\\U+1EE3ng c\\U+1EEDa kh\\U+00F4ng \\U+0111\\U+01B0\\U+1EE3c \\U+00E2m")
    ((and (> ns 0) (or (not ws) (<= ws 0))) "Nh\\U+1EADp b\\U+1EC1 r\\U+1ED9ng c\\U+1EEDa s\\U+1ED5")
    ((and (> nd 0) (or (not wd) (<= wd 0))) "Nh\\U+1EADp b\\U+1EC1 r\\U+1ED9ng c\\U+1EEDa \\U+0111i")
    ((or (= vs 'LOI) (= vd 'LOI)) "\\U+00D4 \\U+0111\\U+1EB7t c\\U+1EEDa ghi d\\U+1EA1ng 1,3 (s\\U+1ED1 nguy\\U+00EAn; 0 ho\\U+1EB7c tr\\U+1ED1ng = t\\U+1EF1 \\U+0111\\U+1EB7t)")
    ;; ghi ít ô hơn số cửa: các cửa còn lại tự đặt
    ((> (length vs) ns) (strcat "\\U+00D4 c\\U+1EEDa s\\U+1ED5: ghi " (itoa (length vs)) " \\U+00F4 nh\\U+01B0ng ch\\U+1EC9 c\\U+00F3 " (itoa ns) " c\\U+1EEDa s\\U+1ED5"))
    ((> (length vd) nd) (strcat "\\U+00D4 c\\U+1EEDa \\U+0111i: ghi " (itoa (length vd)) " \\U+00F4 nh\\U+01B0ng ch\\U+1EC9 c\\U+00F3 " (itoa nd) " c\\U+1EEDa \\U+0111i"))
    ((< (setq S (- L vk:do-rong) R (- S (* ns (if ws ws 0)) (* nd (if wd wd 0)))) -1e-6)
     (strcat "V\\U+00E1ch qu\\U+00E1 ng\\U+1EAFn: c\\U+1EEDa chi\\U+1EBFm " (vk:so (- S R)) " > kho\\U+1EA3ng chia " (vk:so S)))
    (T
     (setq n (if (< R 1e-6) 0 (1+ (fix (/ R vk:toi-da))))
           tong (+ n ns nd)
           b (if (> n 0) (/ R n) 0.0))
     ;; ô cố định do người dùng ghi
     (foreach x (append (mapcar '(lambda (k) (cons k "S")) vs) (mapcar '(lambda (k) (cons k "D")) vd))
       (cond
         ((> (car x) tong) (setq co-dinh 'LOI-NGOAI))
         ((and (listp co-dinh) (assoc (car x) co-dinh)) (setq co-dinh 'LOI-TRUNG))
         ((listp co-dinh) (setq co-dinh (cons x co-dinh)))))
     (cond
       ((= co-dinh 'LOI-NGOAI) (strcat "\\U+00D4 \\U+0111\\U+1EB7t c\\U+1EEDa ph\\U+1EA3i t\\U+1EEB 1 \\U+0111\\U+1EBFn " (itoa tong)))
       ((= co-dinh 'LOI-TRUNG) "Hai c\\U+1EEDa tr\\U+00F9ng m\\U+1ED9t \\U+00F4")
       (T
        ;; cửa không ghi ô: rải đều vào các ô còn trống (cửa đi trước, cửa sổ sau)
        (setq i 1)
        (repeat tong (if (not (assoc i co-dinh)) (setq tu-do (cons i tu-do))) (setq i (1+ i)))
        (setq tu-do (reverse tu-do)
              tu-dong (append (vk:lap (- nd (length vd)) "D") (vk:lap (- ns (length vs)) "S"))
              i 0)
        (foreach x tu-dong
          (setq k (nth (fix (/ (* (+ i 0.5) (length tu-do)) (length tu-dong))) tu-do)
                co-dinh (cons (cons k x) co-dinh)
                i (1+ i)))
        (setq i 1)
        (repeat tong
          (setq x (cdr (assoc i co-dinh))
                o (cons (cond ((= x "S") (list "S" ws)) ((= x "D") (list "D" wd)) (T (list "K" b))) o)
                i (1+ i)))
        (setq o (reverse o) tam (list (/ vk:do-rong 2.0)))
        (foreach x o (setq tam (cons (+ (car tam) (cadr x)) tam)))
        (list o (reverse tam) b n))
     ))
  )
)

;;; ---------------------------------------------------------------- block nhúng sẵn
;;; Định nghĩa block VK_*, kiểu nét, layer A-Window, kiểu chữ + kiểu dim "dim cua" NHÚNG trong file này
;;; (biến vk:dl-* ở cuối file, sinh bằng scripts\nhung_block.ps1) -> chép VK.lsp sang máy khác là chạy được,
;;; không cần file thư viện ngoài (người dùng chốt 28/10/2026).
(defun vk:du-block ()
  (and (tblsearch "BLOCK" "VK_DoDung") (tblsearch "BLOCK" "VK_CuaSoMo") (tblsearch "BLOCK" "VK_CuaDi")))

;;; HATCH trước khi entmake (một đối tượng lỗi làm hỏng cả định nghĩa block đang tạo):
;;;   - (97 . n): số đối tượng biên liên kết; tham chiếu (330) không mang theo được -> đặt 0
;;;   - góc cung biên (50 / 51) đưa về [0, 2π), giữ nguyên hiệu số -> cùng hình (entget có thể trả góc > 2π)
(defun vk:sua-hatch (ed / a out)
  (foreach p ed
    (cond
      ((= (car p) 97) (setq out (cons '(97 . 0) out)))
      ((= (car p) 50)
       (setq a (cdr p))
       (while (>= a (* 2 pi)) (setq a (- a (* 2 pi))))
       (while (< a 0.0) (setq a (+ a (* 2 pi))))
       (setq out (cons (cons 50 a) out) a (- a (cdr p))))
      ((and (= (car p) 51) a) (setq out (cons (cons 51 (+ (cdr p) a)) out) a nil))
      (T (setq out (cons p out)))))
  (reverse out)
)

;;; Tạo những gì bản vẽ còn thiếu; cái đã có (cùng tên) giữ nguyên, không định nghĩa lại. Trả về T nếu đủ block.
(defun vk:nap-thu-vien (/ ten loi ds-cu blk)
  ;; kiểu nét dùng trong block (CENTER, HIDDEN...)
  (foreach ed vk:dl-ltype
    (if (not (tblsearch "LTYPE" (cdr (assoc 2 ed)))) (entmake ed)))
  (if (not (tblsearch "LAYER" vk:layer)) (entmake vk:dl-layer))
  ;; block VK_*
  (foreach blk vk:dl-block
    (setq ten (car blk) loi 0)
    (if (not (tblsearch "BLOCK" ten))
      (progn
        (entmake (list '(0 . "BLOCK") (cons 2 ten) '(70 . 0) '(10 0.0 0.0 0.0)))
        (foreach ed (cdr blk)
          (if (= "HATCH" (cdr (assoc 0 ed))) (setq ed (vk:sua-hatch ed)))
          (if (not (entmake ed)) (setq loi (1+ loi))))
        (entmake '((0 . "ENDBLK")))
        (if (> loi 0) (princ (strcat "\n" ten ": " (itoa loi) " \\U+0111\\U+1ED1i t\\U+01B0\\U+1EE3ng kh\\U+00F4ng t\\U+1EA1o \\U+0111\\U+01B0\\U+1EE3c"))))))
  ;; kiểu chữ + kiểu dim "dim cua": đặt các biến DIM* theo dữ liệu, lưu kiểu, rồi trả lại kiểu đang dùng
  (if (not (tblsearch "STYLE" (cdr (assoc 2 vk:dl-style)))) (entmake vk:dl-style))
  (if (not (tblsearch "DIMSTYLE" vk:dimstyle))
    (progn
      (setq ds-cu (getvar "DIMSTYLE"))
      (foreach p vk:dl-dimvar (vl-catch-all-apply 'setvar (list (car p) (cdr p))))
      (command "_.-DIMSTYLE" "_S" vk:dimstyle)
      (if (tblsearch "DIMSTYLE" ds-cu) (command "_.-DIMSTYLE" "_R" ds-cu))))
  (if (not (vk:du-block)) (princ "\nKh\\U+00F4ng t\\U+1EA1o \\U+0111\\U+01B0\\U+1EE3c block VK_DoDung / VK_CuaSoMo / VK_CuaDi."))
  (vk:du-block)
)

;;; ---------------------------------------------------------------- kéo giãn block cửa
;;; Block cửa có 2 đố ở x = 0 và x = W0. Đổi bề rộng tâm-tâm thành W: phần đố trái (x <= a) giữ nguyên,
;;; đố phải (x >= W0 - a) dời W - W0, phần cánh ở giữa giãn theo tỉ lệ k; cung lớn (r > 200, cung mở cánh)
;;; nhân bán kính theo k. Toạ độ LWPOLYLINE / ARC / CIRCLE / HATCH theo OCS: pháp tuyến -Z thì x đảo dấu.
(defun vk:fx (x)
  (cond
    ((<= x vk:nua-do) x)
    ((>= x (- vk:w0 vk:nua-do)) (+ x (- vk:w vk:w0)))
    (T (+ vk:nua-do (* (- x vk:nua-do) vk:k)))
  )
)

(defun vk:keo-dxf (ed / ex gs loai out)
  (setq ex (cdr (assoc 210 ed))
        gs (if (and ex (< (caddr ex) 0)) -1.0 1.0)
        loai (cdr (assoc 0 ed)))
  (foreach p ed
    (cond
      ((member (car p) '(-1 5 330 360 102)) nil)
      ((and (member (car p) '(10 11)) (member loai '("LINE" "LWPOLYLINE" "ARC" "CIRCLE" "HATCH" "POINT")))
       (setq out (cons (cons (car p) (cons (* gs (vk:fx (* gs (cadr p)))) (cddr p))) out)))
      ((and (= (car p) 40) (member loai '("ARC" "CIRCLE")) (> (cdr p) 200.0))
       (setq out (cons (cons 40 (* vk:k (cdr p))) out)))
      (T (setq out (cons p out)))))
  (reverse out)
)

;;; Trả về tên block cửa đúng bề rộng w (tạo block kéo giãn nếu chưa có)
(defun vk:block-cua (goc w0 w / ten e loi)
  (if (equal w w0 1e-6)
    goc
    (progn
      (setq ten (strcat goc "_" (vl-string-subst "_" "," (vk:so w))))
      (if (not (tblsearch "BLOCK" ten))
        (progn
          (setq vk:w0 w0 vk:w w vk:k (/ (- w (* 2 vk:nua-do)) (- w0 (* 2 vk:nua-do))) loi 0)
          (entmake (list '(0 . "BLOCK") (cons 2 ten) '(70 . 0) '(10 0.0 0.0 0.0)))
          (setq e (cdr (assoc -2 (tblsearch "BLOCK" goc))))
          (while e
            (if (not (entmake (vk:keo-dxf (entget e)))) (setq loi (1+ loi)))
            (setq e (entnext e)))
          (entmake '((0 . "ENDBLK")))
          (if (> loi 0) (princ (strcat "\n" ten ": " (itoa loi) " \\U+0111\\U+1ED1i t\\U+01B0\\U+1EE3ng kh\\U+00F4ng ch\\U+00E9p \\U+0111\\U+01B0\\U+1EE3c")))))
      ten))
)

;;; ---------------------------------------------------------------- dựng vách
(defun vk:ten-block (goc / ten i)
  (setq ten goc i 2)
  (while (tblsearch "BLOCK" ten) (setq ten (strcat goc " (" (itoa i) ")") i (1+ i)))
  ten
)

;;; Nội dung vách dựng bằng ActiveX (vla-*) thẳng vào một block (định nghĩa mới, hoặc bản *U của block động khi
;;; kéo grip): không gọi lệnh qua dòng lệnh nên chạy được cả trong reactor.
(defun vk:doc () (vla-get-ActiveDocument (vlax-get-acad-object)))

(defun vk:mang (ds)
  (vlax-make-variant (vlax-safearray-fill (vlax-make-safearray vlax-vbDouble (cons 0 (1- (length ds)))) ds)))

(defun vk:chen (blk ten x sy / e)
  (setq e (vla-InsertBlock blk (vlax-3d-point x 0.0 0.0) ten 1.0 sy 1.0 0.0))
  (vla-put-Layer e vk:layer)
)

(defun vk:dim (blk p q y / e)
  (setq e (vla-AddDimRotated blk (vlax-3d-point p 0.0 0.0) (vlax-3d-point q 0.0 0.0)
                             (vlax-3d-point (/ (+ p q) 2.0) y 0.0) 0.0))
  (if (tblsearch "DIMSTYLE" vk:dimstyle) (vla-put-StyleName e vk:dimstyle))
  (vla-put-Layer e vk:layer-dim)
)

;;; Vẽ vách (kết quả vk:chia kq, dài L, lật lat) vào block blk, gốc toạ độ = mép ngoài đầu vách
(defun vk:ve-vao (blk kq L lat / o tam sy i x0 w ten-so ten-di e)
  (setq o (car kq) tam (cadr kq) sy (if lat -1.0 1.0))
  (setq ten-so (if (assoc "S" o) (vk:block-cua "VK_CuaSoMo" vk:so-goc (cadr (assoc "S" o))))
        ten-di (if (assoc "D" o) (vk:block-cua "VK_CuaDi" vk:di-goc (cadr (assoc "D" o)))))
  (setq i 0)
  (foreach x o
    (setq x0 (nth i tam) w (cadr x))
    (cond
      ((= (car x) "S") (vk:chen blk ten-so x0 sy))
      ((= (car x) "D") (vk:chen blk ten-di x0 sy))
      (T
       (foreach k vk:kinh
         (setq e (vla-AddLightWeightPolyline blk
                   (vk:mang (list (+ x0 (/ vk:do-rong 2.0)) (* sy (car k))
                                  (- (+ x0 w) (/ vk:do-rong 2.0)) (* sy (car k))
                                  (- (+ x0 w) (/ vk:do-rong 2.0)) (* sy (cadr k))
                                  (+ x0 (/ vk:do-rong 2.0)) (* sy (cadr k))))))
         (vla-put-Closed e :vlax-true)
         (vla-put-Layer e vk:layer))))
    (setq i (1+ i)))
  ;; đố: mọi tâm đố không thuộc block cửa
  (setq i 0)
  (foreach x0 tam
    (if (not (or (and (> i 0) (member (car (nth (1- i) o)) '("S" "D")))
                 (and (< i (length o)) (member (car (nth i o)) '("S" "D")))))
      (vk:chen blk "VK_DoDung" x0 sy))
    (setq i (1+ i)))
  ;; kích thước kiểm tra: chuỗi đố + tổng, kiểu "dim cua", layer Defpoints
  (setq x0 0.0)
  (foreach x (append tam (list L))
    (vk:dim blk x0 x (* sy vk:dim-chuoi))
    (setq x0 x))
  (vk:dim blk 0.0 L (* sy vk:dim-tong))
)

;;; ---------------------------------------------------------------- block động (kéo grip chiều dài)
;;; Người dùng chốt 29/10/2026: block vách có grip ở điểm cuối; kéo grip -> đố chia lại đúng quy tắc (ô < 1200,
;;; chia đều), cửa sổ / cửa đi giữ đúng ô thứ k (ô không còn thì tự đặt lại).
;;;   - Tham số Linear "ChieuDai" (0,0)-(L,0), 1 grip ở điểm cuối + Stretch action quanh đầu cuối: tạo bằng
;;;     -BEDIT / BPARAMETER / BACTION (LISP không có hàm tạo tham số động). Không có VK.lsp thì kéo grip chỉ
;;;     giãn ô cuối.
;;;   - Thông số cửa lưu ở XData "ARCHIVINA_VK" của bản chèn. Reactor ghi lại bản chèn vách bị sửa; hết lệnh
;;;     (kéo grip, Properties...) thì so ChieuDai với chiều dài đã lưu, khác thì chia lại và vẽ lại nội dung
;;;     bản *U của bản chèn đó (block gốc giữ nguyên). Cửa không còn vừa -> trả ChieuDai về chiều dài cũ.
(setq vk:app "ARCHIVINA_VK" vk:tham-so "ChieuDai")

;;; Gắn tham số + Stretch action vào định nghĩa block ten (đang có nội dung vách dài L). Trả về T nếu xong.
(defun vk:lam-dong (ten L lat wmax / sy off big)
  (setq sy (if lat -1.0 1.0)
        ;; nhãn tham số phía không có dim, ra ngoài cung mở cánh cửa (bán kính tới bề rộng cửa)
        off (* -1.0 sy (+ 900.0 wmax))
        big (+ 1500.0 wmax))
  (cond
    ((/= 0 (getvar "BLOCKEDITLOCK")) nil)
    (T
     (command "_.-BEDIT" ten)
     (if (/= 1 (getvar "BLOCKEDITOR"))
       nil
       (progn
         (command "_.ZOOM" "_E")
         (command "_.BPARAMETER" "_L" "_L" vk:tham-so "_non" '(0.0 0.0) "_non" (list L 0.0)
                  "_non" (list (/ L 2.0) off) "1")
         (if (> (logand 1 (getvar "CMDACTIVE")) 0) (command))
         (command "_.ZOOM" "_E")
         ;; chọn tham số bằng điểm trên nhãn; khung kéo giãn + đối tượng kéo: quanh đầu cuối vách
         (command "_.BACTION" "_non" (list (/ L 2.0) off) "_T" "_S"
                  "_non" (list (- L 80.0) (- big)) "_non" (list (+ L 300.0) big)
                  "_C" "_non" (list (- L 80.0) (- big)) "_non" (list (+ L 300.0) big) "")
         (if (> (logand 1 (getvar "CMDACTIVE")) 0) (command))
         (command "_.BSAVE")
         (if (> (logand 1 (getvar "CMDACTIVE")) 0) (command))
         (command "_.BCLOSE")
         (if (> (logand 1 (getvar "CMDACTIVE")) 0) (command))
         (= 0 (getvar "BLOCKEDITOR"))))))
)

(defun vk:prop (o / p)
  (if (= :vlax-true (vla-get-IsDynamicBlock o))
    (vl-some '(lambda (x) (if (= (strcase (vla-get-PropertyName x)) (strcase vk:tham-so)) x))
             (vlax-invoke o 'GetDynamicBlockProperties)))
)

;;; XData bản chèn: (L lat ns ws "ô sổ" nd wd "ô đi"), ô = vị trí thực tế sau khi chia (vd. "3" / "2,5")
(defun vk:o-cua (o loai / i s)
  (setq i 1)
  (foreach x o
    (if (= (car x) loai) (setq s (strcat (if s (strcat s ",") "") (itoa i))))
    (setq i (1+ i)))
  (if s s "")
)

(defun vk:dat-xd (obj kq L lat / o ds ma gt)
  (if (not (tblsearch "APPID" vk:app)) (regapp vk:app))
  (setq o (car kq)
        ds (list (cons 1001 vk:app) (cons 1040 L) (cons 1070 (if lat 1 0))
                 (cons 1070 (length (vl-remove-if-not '(lambda (x) (= (car x) "S")) o)))
                 (cons 1040 (if (assoc "S" o) (cadr (assoc "S" o)) 0.0)) (cons 1000 (vk:o-cua o "S"))
                 (cons 1070 (length (vl-remove-if-not '(lambda (x) (= (car x) "D")) o)))
                 (cons 1040 (if (assoc "D" o) (cadr (assoc "D" o)) 0.0)) (cons 1000 (vk:o-cua o "D"))))
  (setq ma (vlax-make-safearray vlax-vbInteger (cons 0 (1- (length ds))))
        gt (vlax-make-safearray vlax-vbVariant (cons 0 (1- (length ds)))))
  (vlax-safearray-fill ma (mapcar 'car ds))
  (vlax-safearray-fill gt (mapcar '(lambda (x) (vlax-make-variant (cdr x))) ds))
  (vla-SetXData obj ma gt)
)

;;; -> (L lat ns ws vs nd wd vd) hoặc nil
(defun vk:doc-xd (e / xd)
  (if (setq xd (cdr (assoc vk:app (cdr (assoc -3 (entget e (list vk:app)))))))
    (if (= (length xd) 8)
      (list (cdr (nth 0 xd)) (= 1 (cdr (nth 1 xd))) (cdr (nth 2 xd)) (cdr (nth 3 xd))
            (vk:doc-vt (cdr (nth 4 xd))) (cdr (nth 5 xd)) (cdr (nth 6 xd)) (vk:doc-vt (cdr (nth 7 xd))))))
)

;;; Chia lại vách e theo ChieuDai hiện tại. Trả về chuỗi báo hoặc nil (không cần làm gì).
(defun vk:keo-lai (e / obj p L1 d kq ten blk ds ds2)
  (setq obj (vlax-ename->vla-object e) p (vk:prop obj) d (vk:doc-xd e))
  (if (and p d (setq L1 (vlax-variant-value (vla-get-Value p))) (not (equal L1 (car d) 0.005)))
    (progn
      (setq kq (vk:chia L1 (nth 2 d) (nth 3 d) (nth 5 d) (nth 6 d) (nth 4 d) (nth 7 d)))
      ;; ô cửa cũ không còn hợp (vách ngắn đi) -> tự đặt lại
      (if (not (listp kq)) (setq kq (vk:chia L1 (nth 2 d) (nth 3 d) (nth 5 d) (nth 6 d) nil nil)))
      (if (not (listp kq))
        (progn
          ;; cửa không vừa: trả về chiều dài cũ rồi vẽ lại đúng như trước
          (vla-put-Value p (vlax-make-variant (car d) vlax-vbDouble))
          (setq ds (strcat "V\\U+00E1ch " (vk:so L1) ": " kq " -> gi\\U+1EEF chi\\U+1EC1u d\\U+00E0i " (vk:so (car d)))
                L1 (car d)
                kq (vk:chia L1 (nth 2 d) (nth 3 d) (nth 5 d) (nth 6 d) (nth 4 d) (nth 7 d)))))
      ;; chỉ ghi vào bản *U riêng của bản chèn; trả về đúng chiều dài gốc thì AutoCAD dùng lại block gốc
      (setq ten (vla-get-Name obj))
      (if (and (listp kq) (= "*" (substr ten 1 1)))
        (progn
          (setq blk (vla-Item (vla-get-Blocks (vk:doc)) ten))
          (vlax-for x blk (setq ds2 (cons x ds2)))
          (foreach x ds2 (vla-Delete x))
          (vk:ve-vao blk kq L1 (nth 1 d))
          (vla-Update obj)))
      (if (listp kq) (vk:dat-xd obj kq L1 (nth 1 d)))
      (cond
        (ds (strcat "VK: " ds))
        ((listp kq)
         (strcat "VK: v\\U+00E1ch k\\U+00E9o th\\U+00E0nh " (vk:so L1) " -> " (itoa (length (cadr kq))) " \\U+0111\\U+1ED1, "
                 (itoa (nth 3 kq)) " \\U+00F4 k\\U+00EDnh" (if (> (nth 3 kq) 0) (strcat " \\U+00D7 " (vk:so (nth 2 kq))) "")
                 " [" (vk:chuoi (car kq)) "]")))))
)

;;; Reactor: ghi handle bản chèn bị sửa; hết lệnh thì xử lý (bỏ qua khi UNDO / REDO: Undo tự trả nội dung)
;;; reactor database gọi (r (list database đối-tượng)), đối tượng là ename. KHÔNG đọc đối tượng ở đây
;;; (entget trong lúc SAVEAS làm AutoCAD lỗi 0xC0000005, thử 29/10/2026): chỉ ghi ename, lọc khi hết lệnh;
;;; bỏ qua cả khi đang lưu bản vẽ.
(defun vk:r-sua (r ds / obj)
  (if (not (or *vk-dang-sua* *vk-dang-luu*))
    (if (= 'ENAME (type (setq obj (cadr ds))))
      (setq *vk-cho* (cons obj *vk-cho*))))
)

(defun vk:r-luu (r ds) (setq *vk-dang-luu* T))
(defun vk:r-luu-xong (r ds) (setq *vk-dang-luu* nil *vk-cho* nil))

(defun vk:xu-ly-cho (/ ds kq)
  (setq ds *vk-cho* *vk-cho* nil *vk-dang-sua* T)
  (foreach e ds
    (if (and (= 'ENAME (type e)) (entget e)
             (wcmatch (strcase (vl-catch-all-apply 'vla-get-EffectiveName (list (vlax-ename->vla-object e))))
                      "VACH KINH*"))
      (progn
        (setq kq (vl-catch-all-apply 'vk:keo-lai (list e)))
        (cond
          ((vl-catch-all-error-p kq) (princ (strcat "\nVK: l\\U+1ED7i chia l\\U+1EA1i v\\U+00E1ch: " (vl-catch-all-error-message kq))))
          (kq (princ (strcat "\n" kq)))))))
  (setq *vk-dang-sua* nil)
  (princ)
)

;;; Bản chèn vách (có XData) mà ChieuDai khác chiều dài đã lưu -> cần chia lại. Chỉ ĐỌC, gọi được trong reactor.
(defun vk:can-chia (e / d p)
  (and (= 'ENAME (type e)) (entget e) (= "INSERT" (cdr (assoc 0 (entget e)))) (setq d (vk:doc-xd e))
       (setq p (vk:prop (vlax-ename->vla-object e)))
       (not (equal (vlax-variant-value (vla-get-Value p)) (car d) 0.005)))
)

;;; Hết lệnh: KHÔNG sửa bản vẽ ngay trong reactor (sửa nội dung *U trong commandEnded làm hỏng CSDL: AUDIT
;;; dừng giữa chừng, không lưu được - thử 29/10/2026) -> lọc vách cần chia rồi gửi (vk:xu-ly-cho) ra dòng
;;; lệnh, AutoCAD chạy ngay sau khi lệnh hiện tại xong hẳn.
(defun vk:r-xong (r cmd / ds)
  (if *vk-cho*
    (if (or *vk-dang-sua* (member (strcase (car cmd)) '("U" "UNDO" "REDO" "MREDO" "VK")))
      (setq *vk-cho* nil)
      (progn
        (setq ds *vk-cho* *vk-cho* nil)
        (foreach e ds
          (if (and (not (member e *vk-cho*)) (= T (vl-catch-all-apply 'vk:can-chia (list e))))
            (setq *vk-cho* (cons e *vk-cho*))))
        (if *vk-cho* (vla-SendCommand (vk:doc) "(vk:xu-ly-cho)\n")))))
)

(defun vk:r-huy (r cmd) (setq *vk-cho* nil))

(defun vk:bat-reactor ()
  (if (not (and *vk-r-db* (vlr-added-p *vk-r-db*)))
    (setq *vk-r-db* (vlr-acdb-reactor nil '((:vlr-objectModified . vk:r-sua)))))
  (if (not (and *vk-r-luu* (vlr-added-p *vk-r-luu*)))
    (setq *vk-r-luu* (vlr-editor-reactor nil '((:vlr-beginSave . vk:r-luu) (:vlr-saveComplete . vk:r-luu-xong)))))
  (if (not (and *vk-r-lenh* (vlr-added-p *vk-r-lenh*)))
    (setq *vk-r-lenh* (vlr-command-reactor nil '((:vlr-commandEnded . vk:r-xong)
                                                 (:vlr-commandCancelled . vk:r-huy)
                                                 (:vlr-commandFailed . vk:r-huy)))))
)

;;; kq = kết quả vk:chia; L dài; lat T/nil; pt điểm đầu vách (WCS); goc radian. Trả về tên block vách hoặc nil.
;;; Định nghĩa block "VACH KINH <dài>" dựng bằng vla (vk:ve-vao), gắn tham số động (vk:lam-dong), chèn tại pt
;;; góc goc, ghi XData thông số cửa. Không còn dùng -BLOCK.
(defun vk:dung (kq L lat pt goc / o ten blk e wmax)
  (setq o (car kq))
  (if (not (tblsearch "LAYER" vk:layer))
    (entmake (list '(0 . "LAYER") '(100 . "AcDbSymbolTableRecord") '(100 . "AcDbLayerTableRecord")
                   (cons 2 vk:layer) '(70 . 0) '(62 . 151) '(6 . "Continuous"))))
  ;; tên block không được có dấu phẩy: chiều dài lẻ 4210,53 -> "VACH KINH 4210_53"
  ;; (người dùng gặp "Invalid block name" 29/10/2026), cùng cách đặt tên block cửa kéo giãn
  (setq ten (vk:ten-block (strcat "VACH KINH " (vl-string-translate "," "_" (vk:so L))))
        blk (vla-Add (vla-get-Blocks (vk:doc)) (vlax-3d-point 0.0 0.0 0.0) ten)
        wmax (apply 'max (cons 0.0 (mapcar '(lambda (x) (if (/= (car x) "K") (cadr x) 0.0)) o))))
  (vk:ve-vao blk kq L lat)
  (if (not (vk:lam-dong ten L lat wmax))
    (princ "\nVK: kh\\U+00F4ng g\\U+1EAFn \\U+0111\\U+01B0\\U+1EE3c grip k\\U+00E9o chi\\U+1EC1u d\\U+00E0i (Block Editor b\\U+1ECB kho\\U+00E1?) - block v\\U+00E1ch v\\U+1EABn l\\U+00E0 block th\\U+01B0\\U+1EDDng."))
  (entmake (list '(0 . "INSERT") (cons 2 ten) (cons 8 vk:layer) (cons 10 pt)
                 '(41 . 1.0) '(42 . 1.0) '(43 . 1.0) (cons 50 goc)))
  (setq e (entlast))
  (if (and e (= ten (cdr (assoc 2 (entget e)))))
    (progn (vk:dat-xd (vlax-ename->vla-object e) kq L lat) ten))
)

;;; Chuỗi tóm tắt: "1058,75 | SO 1000 | ..."
(defun vk:chuoi (o / s)
  (foreach x o
    (setq s (strcat (if s (strcat s " | ") "")
                    (cond ((= (car x) "S") "SO ") ((= (car x) "D") "DI ") (T ""))
                    (vk:so (cadr x)))))
  s
)

;;; Chạy đủ (dùng chung cho lệnh VK và chạy thử không hộp thoại). pt / goc nil -> hỏi người dùng.
;;; Nhóm undo bằng vla-StartUndoMark, không gọi lệnh UNDO qua dòng lệnh: lệnh UNDO có lúc dừng ở dòng hỏi
;;; "Enter the number of operations to undo" (người dùng báo 29/10/2026, sau khi pick 2 điểm).
(defun vk:thuc-hien (kq L lat pt goc / *error* bien cu undo ucs p2 ten doc)
  (defun *error* (msg)
    (mapcar 'setvar bien cu)
    (if ucs (command-s "_.UCS" "_P"))
    (if undo (vla-EndUndoMark doc))
    (setq *vk-dang-sua* nil *vk-cho* nil)
    (if (not (wcmatch (strcase msg) "*CANCEL*,*QUIT*,*BREAK*"))
      (princ (strcat "\nL\\U+1ED7i VK: " msg)))
    (princ)
  )
  (setq bien '("CMDECHO" "OSMODE" "CLAYER") cu (mapcar 'getvar bien))
  (setvar "CMDECHO" 0)
  (setvar "OSMODE" 0)
  (setq doc (vla-get-ActiveDocument (vlax-get-acad-object)))
  ;; reactor bỏ qua mọi thay đổi trong lúc đang dựng vách
  (setq *vk-dang-sua* T)
  (if (setq undo (vk:undo-ok)) (vla-StartUndoMark doc))
  (if (= 0 (getvar "WORLDUCS")) (progn (command "_.UCS" "_W") (setq ucs T)))
  (cond
    ((not (vk:nap-thu-vien)) (princ "\nD\\U+1EEBng: thi\\U+1EBFu block VK_DoDung / VK_CuaSoMo / VK_CuaDi."))
    (T
     (if (not pt)
       (progn
         (setvar "OSMODE" (nth 1 cu))
         (setq pt (getpoint "\nCh\\U+1ECDn \\U+0111i\\U+1EC3m \\U+0111\\U+1EA7u v\\U+00E1ch (m\\U+00E9p ngo\\U+00E0i): "))
         (if pt (setq p2 (getpoint pt "\nCh\\U+1ECDn \\U+0111i\\U+1EC3m h\\U+01B0\\U+1EDBng v\\U+00E1ch <theo tr\\U+1EE5c X>: ")))
         (setq goc (if p2 (angle pt p2) 0.0))
         (setvar "OSMODE" 0)))
     (if pt
       (progn
         (setq ten (vk:dung kq L lat (trans pt 1 0) goc))
         (princ (strcat "\nVK: v\\U+00E1ch " (vk:so L) " -> " (itoa (length (cadr kq))) " \\U+0111\\U+1ED1, "
                        (itoa (nth 3 kq)) " \\U+00F4 k\\U+00EDnh"
                        (if (> (nth 3 kq) 0) (strcat " \\U+00D7 " (vk:so (nth 2 kq))) "")
                        "\n    [" (vk:chuoi (car kq)) "]"
                        (if ten (strcat "\n    Block: " ten) "\n    Kh\\U+00F4ng t\\U+1EA1o \\U+0111\\U+01B0\\U+1EE3c block v\\U+00E1ch"))))
       (princ "\n\\U+0110\\U+00E3 hu\\U+1EF7."))))
  (if ucs (command "_.UCS" "_P"))
  (if undo (vla-EndUndoMark doc))
  (setq *vk-dang-sua* nil *vk-cho* nil)
  (mapcar 'setvar bien cu)
  (princ)
)

;;; ---------------------------------------------------------------- pick 2 điểm
;;; Chọn điểm đầu / cuối vách (mép ngoài, theo OSNAP người dùng đang đặt). Trả về (p1 p2 dài): p1 p2 toạ độ
;;; WCS (vk:thuc-hien chuyển UCS về World trước khi dựng), dài đo trên mặt phẳng XY; huỷ / trùng điểm -> nil.
;;; Enter ở điểm đầu = thôi, quay lại bảng.
(defun vk:pick-dai (/ p1 p2 a b)
  (if (and (setq p1 (getpoint "\nCh\\U+1ECDn \\U+0111i\\U+1EC3m \\U+0111\\U+1EA7u v\\U+00E1ch (m\\U+00E9p ngo\\U+00E0i) <Enter = quay l\\U+1EA1i b\\U+1EA3ng>: "))
           (setq p2 (getpoint p1 "\nCh\\U+1ECDn \\U+0111i\\U+1EC3m cu\\U+1ED1i v\\U+00E1ch (m\\U+00E9p ngo\\U+00E0i): ")))
    (progn
      (setq a (trans p1 1 0) b (trans p2 1 0)
            a (list (car a) (cadr a) (caddr a)) b (list (car b) (cadr b) (caddr a)))
      (if (> (distance a b) 1e-6) (list a b (distance a b)))))
)

;;; ---------------------------------------------------------------- hộp thoại
(defun vk:viet-dcl (f / h)
  ;; VK.lsp sinh từ file này đã đổi chữ có dấu thành mã \U+XXXX (chỉ còn ký tự ASCII) -> ghi DCL thường,
  ;; hộp thoại hiện đúng dấu với cả LISPSYS = 0 và 1
  (setq h (open f "w"))
  (foreach s
    '("vk_hop_thoai : dialog {"
      "  label = \"VK - Chia \\U+0111\\U+1ED1 v\\U+00E1ch k\\U+00EDnh\";"
      "  : boxed_column { label = \"V\\U+00E1ch k\\U+00EDnh\";"
      "    : row {"
      "      : edit_box { key = \"dai\"; label = \"Chi\\U+1EC1u d\\U+00E0i v\\U+00E1ch (mm, m\\U+00E9p ngo\\U+00E0i - m\\U+00E9p ngo\\U+00E0i):\"; edit_width = 10; }"
      "      : button { key = \"pick\"; label = \"Pick 2 \\U+0111i\\U+1EC3m <\"; fixed_width = true; }"
      "    }"
      "    : text { key = \"diem\"; width = 62; }"
      "    : text { key = \"thongtin\"; width = 62; }"
      "  }"
      "  : row {"
      "    : boxed_column { label = \"C\\U+1EEDa s\\U+1ED5 m\\U+1EDF\";"
      "      : edit_box { key = \"ns\"; label = \"S\\U+1ED1 l\\U+01B0\\U+1EE3ng:\"; edit_width = 6; }"
      "      : edit_box { key = \"ws\"; label = \"R\\U+1ED9ng t\\U+00E2m - t\\U+00E2m \\U+0111\\U+1ED1 (mm):\"; edit_width = 8; }"
      "      : edit_box { key = \"vs\"; label = \"\\U+1EDE \\U+00F4 th\\U+1EE9 (vd. 1,3; tr\\U+1ED1ng ho\\U+1EB7c 0 = t\\U+1EF1 \\U+0111\\U+1EB7t):\"; edit_width = 8; }"
      "    }"
      "    : boxed_column { label = \"C\\U+1EEDa \\U+0111i\";"
      "      : edit_box { key = \"nd\"; label = \"S\\U+1ED1 l\\U+01B0\\U+1EE3ng:\"; edit_width = 6; }"
      "      : edit_box { key = \"wd\"; label = \"R\\U+1ED9ng t\\U+00E2m - t\\U+00E2m \\U+0111\\U+1ED1 (mm):\"; edit_width = 8; }"
      "      : edit_box { key = \"vd\"; label = \"\\U+1EDE \\U+00F4 th\\U+1EE9 (vd. 2; tr\\U+1ED1ng ho\\U+1EB7c 0 = t\\U+1EF1 \\U+0111\\U+1EB7t):\"; edit_width = 8; }"
      "    }"
      "  }"
      "  : list_box { key = \"ds\"; label = \"Kho\\U+1EA3ng c\\U+00E1ch c\\U+00E1c \\U+0111\\U+1ED1 (t\\U+00E2m - t\\U+00E2m, \\U+00F4 \\U+0111\\U+1EBFm t\\U+1EEB tr\\U+00E1i, k\\U+1EC3 c\\U+1EA3 \\U+00F4 c\\U+1EEDa):\"; height = 12; width = 62; tabs = \"6 20\"; }"
      "  : row {"
      "    : toggle { key = \"lat\"; label = \"L\\U+1EADt v\\U+00E1ch (m\\U+1EB7t k\\U+1EB9p k\\U+00EDnh sang ph\\U+00EDa b\\U+00EAn kia)\"; }"
      "    : button { key = \"tinh\"; label = \"T\\U+00EDnh l\\U+1EA1i\"; fixed_width = true; }"
      "  }"
      "  : text { key = \"loi\"; width = 62; }"
      "  ok_cancel;"
      "}")
    (write-line s h))
  (close h)
)

;;; Đọc các ô nhập -> kết quả chia (danh sách) hoặc chuỗi lỗi; cập nhật bảng
;;; Tính chia với chiều dài L, thông số cửa đọc qua hàm lay (get_tile khi hộp thoại mở)
(defun vk:tinh-tu (lay L / ns nd)
  (setq ns (vk:doc-so (apply lay '("ns"))) nd (vk:doc-so (apply lay '("nd"))))
  (vk:chia L (if ns (fix ns) 0) (vk:doc-so (apply lay '("ws")))
           (if nd (fix nd) 0) (vk:doc-so (apply lay '("wd")))
           (vk:doc-vt (apply lay '("vs"))) (vk:doc-vt (apply lay '("vd"))))
)

(defun vk:cap-nhat (/ L kq i)
  (setq L (vk:doc-so (get_tile "dai"))
        kq (vk:tinh-tu 'get_tile L))
  (start_list "ds")
  (if (listp kq)
    (progn
      (setq i 1)
      (foreach x (car kq)
        (add_list (strcat "\\U+00D4 " (itoa i) "\t"
                          (cond ((= (car x) "S") "C\\U+1EEDa s\\U+1ED5 m\\U+1EDF") ((= (car x) "D") "C\\U+1EEDa \\U+0111i") (T "K\\U+00EDnh"))
                          "\t" (vk:so (cadr x))))
        (setq i (1+ i)))))
  (end_list)
  (if (listp kq)
    (progn
      (set_tile "thongtin" (strcat "S\\U+1ED1 \\U+0111\\U+1ED1: " (itoa (length (cadr kq))) "   |   \\U+00D4 k\\U+00EDnh: " (itoa (nth 3 kq))
                                   (if (> (nth 3 kq) 0) (strcat " \\U+00D7 " (vk:so (nth 2 kq)) " mm") "")
                                   "   |   \\U+0110\\U+1ED1 r\\U+1ED9ng 65, m\\U+1ED7i \\U+00F4 < 1200"))
      (set_tile "loi" ""))
    (progn (set_tile "thongtin" "") (set_tile "loi" (strcat "L\\U+1ED7i: " kq))))
  (set_tile "diem"
    (cond
      ((not vk-diem) "Ch\\U+01B0a c\\U+00F3 chi\\U+1EC1u d\\U+00E0i th\\U+00EC b\\U+1EA5m Pick 2 \\U+0111i\\U+1EC3m (\\U+0111\\U+1EA7u / cu\\U+1ED1i v\\U+00E1ch); nh\\U+1EADp tay th\\U+00EC OK s\\U+1EBD h\\U+1ECFi \\U+0111i\\U+1EC3m \\U+0111\\U+1EB7t")
      ((vk:dung-diem L) "\\U+0110\\U+00E3 pick 2 \\U+0111i\\U+1EC3m: OK l\\U+00E0 d\\U+1EF1ng v\\U+00E1ch \\U+0111\\U+00FAng v\\U+1ECB tr\\U+00ED \\U+0111\\U+00E3 ch\\U+1ECDn")
      (T "Chi\\U+1EC1u d\\U+00E0i \\U+0111\\U+00E3 s\\U+1EEDa tay: OK s\\U+1EBD h\\U+1ECFi l\\U+1EA1i \\U+0111i\\U+1EC3m \\U+0111\\U+1EB7t v\\U+00E1ch")))
  (setq vk-kq kq vk-dai L)
)

;;; Chiều dài L còn khớp 2 điểm đã pick (ô nhập làm tròn 2 chữ số lẻ)
(defun vk:dung-diem (L) (and vk-diem L (equal L (caddr vk-diem) 0.006)))

(defun vk:luu-nho ()
  (setq *vk-nho* (mapcar '(lambda (k) (cons k (get_tile k))) '("dai" "ns" "ws" "vs" "nd" "wd" "vd" "lat"))))

;;; Ghi chiều dài 2 điểm vừa pick vào ô "dai" của bộ nhớ hộp thoại
(defun vk:nho-dai (d)
  (if (not *vk-nho*)
    (setq *vk-nho* '(("dai" . "") ("ns" . "0") ("ws" . "1000") ("vs" . "")
                     ("nd" . "0") ("wd" . "1665") ("vd" . "") ("lat" . "0"))))
  (setq *vk-nho* (subst (cons "dai" (vk:so (caddr d))) (assoc "dai" *vk-nho*) *vk-nho*))
)

;;; Gõ VK -> bảng hiện ra trước: có chiều dài thì nhập, chưa có thì bấm "Pick 2 điểm <" (bảng ẩn, chọn điểm đầu
;;; + điểm cuối vách, bảng mở lại với chiều dài đã điền) -> chọn cửa sổ / cửa đi -> OK dựng vách đúng 2 điểm đã
;;; pick (người dùng chốt 29/10/2026). Hộp thoại đóng với mã 2 khi bấm nút pick.
(defun c:VK (/ f id kq-dlg vk-kq vk-dai vk-diem lat d)
  (setq f (strcat (getvar "TEMPPREFIX") "VK_hop_thoai.dcl"))
  (vk:viet-dcl f)
  (if (< (setq id (load_dialog f)) 0)
    (princ "\nKh\\U+00F4ng m\\U+1EDF \\U+0111\\U+01B0\\U+1EE3c h\\U+1ED9p tho\\U+1EA1i VK.")
    (progn
      (setq kq-dlg 2)
      (while (= kq-dlg 2)
        (setq kq-dlg nil)
        (if (not (new_dialog "vk_hop_thoai" id))
          (princ "\nKh\\U+00F4ng m\\U+1EDF \\U+0111\\U+01B0\\U+1EE3c h\\U+1ED9p tho\\U+1EA1i VK.")
          (progn
            (foreach x (if *vk-nho* *vk-nho*
                         '(("dai" . "") ("ns" . "0") ("ws" . "1000") ("vs" . "")
                           ("nd" . "0") ("wd" . "1665") ("vd" . "") ("lat" . "0")))
              (set_tile (car x) (cdr x)))
            (foreach k '("dai" "ns" "ws" "vs" "nd" "wd" "vd" "tinh")
              (action_tile k "(vk:cap-nhat)"))
            (action_tile "pick" "(vk:luu-nho) (done_dialog 2)")
            (action_tile "accept"
              "(vk:cap-nhat) (if (listp vk-kq) (progn (setq lat (= \"1\" (get_tile \"lat\"))) (vk:luu-nho) (done_dialog 1)))")
            (action_tile "cancel" "(vk:luu-nho) (done_dialog 0)")
            (vk:cap-nhat)
            (setq kq-dlg (start_dialog))
            ;; bấm Pick 2 điểm: pick lại rồi mở lại bảng với chiều dài mới
            (if (and (= kq-dlg 2) (setq d (vk:pick-dai)))
              (progn (setq vk-diem d) (vk:nho-dai d))))))
      (unload_dialog id)
      (if (= kq-dlg 1)
        (if (vk:dung-diem vk-dai)
          (vk:thuc-hien vk-kq vk-dai lat (car vk-diem) (angle (car vk-diem) (cadr vk-diem)))
          (vk:thuc-hien vk-kq vk-dai lat nil nil)))))
  (princ)
)

(vk:bat-reactor)
(princ "\n\\U+0110\\U+00E3 n\\U+1EA1p VK.lsp \\U+2014 g\\U+00F5 VK \\U+0111\\U+1EC3 chia \\U+0111\\U+1ED1 v\\U+00E1ch k\\U+00EDnh (k\\U+00E9o grip cu\\U+1ED1i v\\U+00E1ch \\U+0111\\U+1EC3 \\U+0111\\U+1ED5i chi\\U+1EC1u d\\U+00E0i, \\U+0111\\U+1ED1 t\\U+1EF1 chia l\\U+1EA1i).")
(princ)

;;; ---------------------------------------------------------------- dữ liệu block nhúng (sinh tự động)
(setq vk:dl-block '(
("VK_DoDung"
((0 . "LWPOLYLINE") (100 . "AcDbEntity") (67 . 0) (8 . "A-Window") (62 . 151) (6 . "Continuous") (100 . "AcDbPolyline") (90 . 8) (70 . 1) (43 . 0.0000000000) (38 . 0.0000000000) (39 . 0.0000000000) (10 29.8578888394 -90.5967000000) (40 . 0.0000000000) (41 . 0.0000000000) (42 . 0.4142135624) (91 . 0) (10 30.3578888394 -90.0967000000) (40 . 0.0000000000) (41 . 0.0000000000) (42 . 0.0000000000) (91 . 0) (10 30.3578888394 30.4967000000) (40 . 0.0000000000) (41 . 0.0000000000) (42 . 0.4142135624) (91 . 0) (10 29.8578888394 30.9967000000) (40 . 0.0000000000) (41 . 0.0000000000) (42 . 0.0000000000) (91 . 0) (10 -29.1421111606 30.9967000000) (40 . 0.0000000000) (41 . 0.0000000000) (42 . 0.4142135624) (91 . 0) (10 -29.6421111606 30.4967000000) (40 . 0.0000000000) (41 . 0.0000000000) (42 . 0.0000000000) (91 . 0) (10 -29.6421111606 -90.0967000000) (40 . 0.0000000000) (41 . 0.0000000000) (42 . 0.4142135624) (91 . 0) (10 -29.1421111606 -90.5967000000) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 87) (70 . 1) (43 . 0.0000000000) (38 . 0.0000000000) (39 . 0.0000000000) (10 29.7578888394 34.6967000000) (40 . 0.0000000000) (41 . 0.0000000000) (42 . 0.0000000000) (91 . 0) (10 29.7578888394 34.4967000000) (40 . 0.0000000000) (41 . 0.0000000000) (42 . -0.4142135624) (91 . 0) (10 29.2578888394 33.9967000000) (40 . 0.0000000000) (41 . 0.0000000000) (42 . 0.0000000000) (91 . 0) (10 25.4578888394 33.9967000000) (40 . 0.0000000000) (41 . 0.0000000000) (42 . -0.4142135624) (91 . 0) (10 24.9578888394 34.4967000000) (40 . 0.0000000000) (41 . 0.0000000000) (42 . 0.0000000000) (91 . 0) (10 24.9578888394 34.6967000000) (40 . 0.0000000000) (41 . 0.0000000000) (42 . -0.4142135624) (91 . 0) (10 25.4578888394 35.1967000000) (40 . 0.0000000000) (41 . 0.0000000000) (42 . 0.0000000000) (91 . 0) (10 25.6578888394 35.1967000000) (40 . 0.0000000000) (41 . 0.0000000000) (42 . 0.4142135624) (91 . 0) (10 26.1578888394 35.6967000000) (40 . 0.0000000000) (41 . 0.0000000000) (42 . 0.0000000000) (91 . 0) (10 26.1578888394 35.8967000000) (40 . 0.0000000000) (41 . 0.0000000000) (42 . 0.4142135624) (91 . 0) (10 25.6578888394 36.3967000000) (40 . 0.0000000000) (41 . 0.0000000000) (42 . 0.0000000000) (91 . 0) (10 24.2578888394 36.3967000000) (40 . 0.0000000000) (41 . 0.0000000000) (42 . 0.4142135624) (91 . 0) (10 23.7578888394 35.8967000000) (40 . 0.0000000000) (41 . 0.0000000000) (42 . 0.0000000000) (91 . 0) (10 23.7578888394 34.4967000000) (40 . 0.0000000000) (41 . 0.0000000000) (42 . -0.4142135624) (91 . 0) (10 23.2578888394 33.9967000000) (40 . 0.0000000000) (41 . 0.0000000000) (42 . 0.0000000000) (91 . 0) (10 9.3578888394 33.9967000000) (40 . 0.0000000000) (41 . 0.0000000000) (42 . -0.4142135624) (91 . 0) (10 8.8578888394 34.4967000000) (40 . 0.0000000000) (41 . 0.0000000000) (42 . 0.0000000000) (91 . 0) (10 8.8578888394 55.8967000000) (40 . 0.0000000000) (41 . 0.0000000000) (42 . 0.4142135624) (91 . 0) (10 8.3578888394 56.3967000000) (40 . 0.0000000000) (41 . 0.0000000000) (42 . 0.0000000000) (91 . 0) (10 6.0578936442 56.3967000000) (40 . 0.0000000000) (41 . 0.0000000000) (42 . 0.0000000000) (91 . 0) (10 5.0809431613 54.4427990332) (40 . 0.0000000000) (41 . 0.0000000000) (42 . 0.4142135643) (91 . 0) (10 5.1703858816 54.1744708754) (40 . 0.0000000000) (41 . 0.0000000000) (42 . 0.0000000000) (91 . 0) (10 5.3492713179 54.0850281587) (40 . 0.0000000000) (41 . 0.0000000000) (42 . -0.4142135643) (91 . 0) (10 5.4387140381 53.8167000008) (40 . 0.0000000000) (41 . 0.0000000000) (42 . 0.0000000000) (91 . 0) (10 4.8339926779 52.6072572806) (40 . 0.0000000000) (41 . 0.0000000000) (42 . -0.2840790438) (91 . 0) (10 4.6551072397 52.4966999997) (40 . 0.0000000000) (41 . 0.0000000000) (42 . 0.0000000000) (91 . 0) (10 1.0235742645 52.4966999997) (40 . 0.0000000000) (41 . 0.0000000000) (42 . 0.1989123674) (91 . 0) (10 0.8821529082 52.4381213559) (40 . 0.0000000000) (41 . 0.0000000000) (42 . 0.0000000000) (91 . 0) (10 0.4993101957 52.0552786434) (40 . 0.0000000000) (41 . 0.0000000000) (42 . -0.1989123674) (91 . 0) (10 0.3578888395 51.9966999997) (40 . 0.0000000000) (41 . 0.0000000000) (42 . -0.1989123674) (91 . 0) (10 0.2164674833 52.0552786434) (40 . 0.0000000000) (41 . 0.0000000000) (42 . 0.0000000000) (91 . 0) (10 -0.1663752292 52.4381213559) (40 . 0.0000000000) (41 . 0.0000000000) (42 . 0.1989123674) (91 . 0) (10 -0.3077965854 52.4966999997) (40 . 0.0000000000) (41 . 0.0000000000) (42 . 0.0000000000) (91 . 0) (10 -3.9393295607 52.4966999997) (40 . 0.0000000000) (41 . 0.0000000000) (42 . -0.2840790438) (91 . 0) (10 -4.1182149988 52.6072572805) (40 . 0.0000000000) (41 . 0.0000000000) (42 . 0.0000000000) (91 . 0) (10 -4.7229363593 53.8167000007) (40 . 0.0000000000) (41 . 0.0000000000) (42 . -0.4142135642) (91 . 0) (10 -4.6334936391 54.0850281586) (40 . 0.0000000000) (41 . 0.0000000000) (42 . 0.0000000000) (91 . 0) (10 -4.4546082026 54.1744708755) (40 . 0.0000000000) (41 . 0.0000000000) (42 . 0.4142135641) (91 . 0) (10 -4.3651654824 54.4427990333) (40 . 0.0000000000) (41 . 0.0000000000) (42 . 0.0000000000) (91 . 0) (10 -5.3421159653 56.3967000000) (40 . 0.0000000000) (41 . 0.0000000000) (42 . 0.0000000000) (91 . 0) (10 -7.6421111606 56.3967000000) (40 . 0.0000000000) (41 . 0.0000000000) (42 . 0.4142135624) (91 . 0) (10 -8.1421111606 55.8967000000) (40 . 0.0000000000) (41 . 0.0000000000) (42 . 0.0000000000) (91 . 0) (10 -8.1421111606 34.4967000000) (40 . 0.0000000000) (41 . 0.0000000000) (42 . -0.4142135624) (91 . 0) (10 -8.6421111606 33.9967000000) (40 . 0.0000000000) (41 . 0.0000000000) (42 . 0.0000000000) (91 . 0) (10 -22.5421111606 33.9967000000) (40 . 0.0000000000) (41 . 0.0000000000) (42 . -0.4142135624) (91 . 0) (10 -23.0421111606 34.4967000000) (40 . 0.0000000000) (41 . 0.0000000000) (42 . 0.0000000000) (91 . 0) (10 -23.0421111606 35.8967000000) (40 . 0.0000000000) (41 . 0.0000000000) (42 . 0.4142135624) (91 . 0) (10 -23.5421111606 36.3967000000) (40 . 0.0000000000) (41 . 0.0000000000) (42 . 0.0000000000) (91 . 0) (10 -24.9421111606 36.3967000000) (40 . 0.0000000000) (41 . 0.0000000000) (42 . 0.4142135624) (91 . 0) (10 -25.4421111606 35.8967000000) (40 . 0.0000000000) (41 . 0.0000000000) (42 . 0.0000000000) (91 . 0) (10 -25.4421111606 35.6967000000) (40 . 0.0000000000) (41 . 0.0000000000) (42 . 0.4142135624) (91 . 0) (10 -24.9421111606 35.1967000000) (40 . 0.0000000000) (41 . 0.0000000000) (42 . 0.0000000000) (91 . 0) (10 -24.7421111606 35.1967000000) (40 . 0.0000000000) (41 . 0.0000000000) (42 . -0.4142135624) (91 . 0) (10 -24.2421111606 34.6967000000) (40 . 0.0000000000) (41 . 0.0000000000) (42 . 0.0000000000) (91 . 0) (10 -24.2421111606 34.4967000000) (40 . 0.0000000000) (41 . 0.0000000000) (42 . -0.4142135624) (91 . 0) (10 -24.7421111606 33.9967000000) (40 . 0.0000000000) (41 . 0.0000000000) (42 . 0.0000000000) (91 . 0) (10 -28.5421111606 33.9967000000) (40 . 0.0000000000) (41 . 0.0000000000) (42 . -0.4142135624) (91 . 0) (10 -29.0421111606 34.4967000000) (40 . 0.0000000000) (41 . 0.0000000000) (42 . 0.0000000000) (91 . 0) (10 -29.0421111606 34.6967000000) (40 . 0.0000000000) (41 . 0.0000000000) (42 . -0.4142135624) (91 . 0) (10 -28.5421111606 35.1967000000) (40 . 0.0000000000) (41 . 0.0000000000) (42 . 0.0000000000) (91 . 0) (10 -28.3421111606 35.1967000000) (40 . 0.0000000000) (41 . 0.0000000000) (42 . 0.4142135624) (91 . 0) (10 -27.8421111606 35.6967000000) (40 . 0.0000000000) (41 . 0.0000000000) (42 . 0.0000000000) (91 . 0) (10 -27.8421111606 35.8967000000) (40 . 0.0000000000) (41 . 0.0000000000) (42 . 0.4142135624) (91 . 0) (10 -28.3421111606 36.3967000000) (40 . 0.0000000000) (41 . 0.0000000000) (42 . 0.0000000000) (91 . 0) (10 -30.4421111606 36.3967000000) (40 . 0.0000000000) (41 . 0.0000000000) (42 . -0.4142135624) (91 . 0) (10 -30.9421111606 36.8967000000) (40 . 0.0000000000) (41 . 0.0000000000) (42 . 0.0000000000) (91 . 0) (10 -30.9421111606 37.8967000000) (40 . 0.0000000000) (41 . 0.0000000000) (42 . 0.4142135624) (91 . 0) (10 -31.4421111606 38.3967000000) (40 . 0.0000000000) (41 . 0.0000000000) (42 . 0.0000000000) (91 . 0) (10 -31.6421111606 38.3967000000) (40 . 0.0000000000) (41 . 0.0000000000) (42 . 0.4142135624) (91 . 0) (10 -32.1421111606 37.8967000000) (40 . 0.0000000000) (41 . 0.0000000000) (42 . 0.0000000000) (91 . 0) (10 -32.1421111606 33.9967000000) (40 . 0.0000000000) (41 . 0.0000000000) (42 . 0.0000000000) (91 . 0) (10 -32.1421111606 -93.0967000000) (40 . 0.0000000000) (41 . 0.0000000000) (42 . 0.4142135624) (91 . 0) (10 -31.6421111606 -93.5967000000) (40 . 0.0000000000) (41 . 0.0000000000) (42 . 0.0000000000) (91 . 0) (10 32.3578888394 -93.5967000000) (40 . 0.0000000000) (41 . 0.0000000000) (42 . 0.4142135624) (91 . 0) (10 32.8578888394 -93.0967000000) (40 . 0.0000000000) (41 . 0.0000000000) (42 . 0.0000000000) (91 . 0) (10 32.8578888394 33.9967000000) (40 . 0.0000000000) (41 . 0.0000000000) (42 . 0.0000000000) (91 . 0) (10 32.8578888394 37.8967000000) (40 . 0.0000000000) (41 . 0.0000000000) (42 . 0.4142135624) (91 . 0) (10 32.3578888394 38.3967000000) (40 . 0.0000000000) (41 . 0.0000000000) (42 . 0.0000000000) (91 . 0) (10 32.1578888394 38.3967000000) (40 . 0.0000000000) (41 . 0.0000000000) (42 . 0.4142135624) (91 . 0) (10 31.6578888394 37.8967000000) (40 . 0.0000000000) (41 . 0.0000000000) (42 . 0.0000000000) (91 . 0) (10 31.6578888394 36.8967000000) (40 . 0.0000000000) (41 . 0.0000000000) (42 . -0.4142135624) (91 . 0) (10 31.1578888394 36.3967000000) (40 . 0.0000000000) (41 . 0.0000000000) (42 . 0.0000000000) (91 . 0) (10 29.0578888394 36.3967000000) (40 . 0.0000000000) (41 . 0.0000000000) (42 . 0.4142135624) (91 . 0) (10 28.5578888394 35.8967000000) (40 . 0.0000000000) (41 . 0.0000000000) (42 . 0.0000000000) (91 . 0) (10 28.5578888394 35.6967000000) (40 . 0.0000000000) (41 . 0.0000000000) (42 . 0.4142135624) (91 . 0) (10 29.0578888394 35.1967000000) (40 . 0.0000000000) (41 . 0.0000000000) (42 . 0.0000000000) (91 . 0) (10 29.2578888394 35.1967000000) (40 . 0.0000000000) (41 . 0.0000000000) (42 . -0.4142135624) (91 . 0) (210 0.0000000000 0.0000000000 1.0000000000))
((0 . "LWPOLYLINE") (100 . "AcDbEntity") (67 . 0) (8 . "A-Window") (62 . 151) (6 . "Continuous") (100 . "AcDbPolyline") (90 . 17) (70 . 1) (43 . 0.0000000000) (38 . 0.0000000000) (39 . 0.0000000000) (10 0.3578888395 47.4966999996) (40 . 0.0000000000) (41 . 0.0000000000) (42 . 0.0000000000) (91 . 0) (10 -2.8235760300 47.4966999996) (40 . 0.0000000000) (41 . 0.0000000000) (42 . -0.2914734196) (91 . 0) (10 -3.2767299235 47.7853908688) (40 . 0.0000000000) (41 . 0.0000000000) (42 . 0.0000000000) (91 . 0) (10 -4.1732615427 49.7080091306) (40 . 0.0000000000) (41 . 0.0000000000) (42 . 0.2914734196) (91 . 0) (10 -4.6264154362 49.9966999997) (40 . 0.0000000000) (41 . 0.0000000000) (42 . 0.0000000000) (91 . 0) (10 -5.6421111605 49.9966999997) (40 . 0.0000000000) (41 . 0.0000000000) (42 . 0.4142135624) (91 . 0) (10 -6.1421111605 49.4966999997) (40 . 0.0000000000) (41 . 0.0000000000) (42 . 0.0000000000) (91 . 0) (10 -6.1421111605 34.4967000000) (40 . 0.0000000000) (41 . 0.0000000000) (42 . 0.4142135624) (91 . 0) (10 -5.6421111605 33.9967000000) (40 . 0.0000000000) (41 . 0.0000000000) (42 . 0.0000000000) (91 . 0) (10 6.3578888395 33.9967000000) (40 . 0.0000000000) (41 . 0.0000000000) (42 . 0.4142135624) (91 . 0) (10 6.8578888395 34.4967000000) (40 . 0.0000000000) (41 . 0.0000000000) (42 . 0.0000000000) (91 . 0) (10 6.8578888395 49.4966999997) (40 . 0.0000000000) (41 . 0.0000000000) (42 . 0.4142135624) (91 . 0) (10 6.3578888395 49.9966999997) (40 . 0.0000000000) (41 . 0.0000000000) (42 . 0.0000000000) (91 . 0) (10 5.3421931154 49.9966999997) (40 . 0.0000000000) (41 . 0.0000000000) (42 . 0.2914734196) (91 . 0) (10 4.8890392219 49.7080091306) (40 . 0.0000000000) (41 . 0.0000000000) (42 . 0.0000000000) (91 . 0) (10 3.9925076027 47.7853908688) (40 . 0.0000000000) (41 . 0.0000000000) (42 . -0.2914734196) (91 . 0) (10 3.5393537092 47.4966999996) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 12) (70 . 1) (43 . 0.0000000000) (38 . 0.0000000000) (39 . 0.0000000000) (10 6.1467510526 61.6983038651) (40 . 0.0000000000) (41 . 0.0000000000) (42 . 0.2849552787) (91 . 0) (10 6.2578888319 61.8774783771) (40 . 0.0000000000) (41 . 0.0000000000) (42 . 0.0000000000) (91 . 0) (10 6.2578888319 61.7734539608) (40 . 0.0000000000) (41 . 0.0000000000) (42 . 0.5564744028) (91 . 0) (10 5.5357332802 62.2213902406) (40 . 0.0000000000) (41 . 0.0000000000) (42 . 0.0000000000) (91 . 0) (10 0.5800443918 62.7635991465) (40 . 0.0000000000) (41 . 0.0000000000) (42 . -0.2343570514) (91 . 0) (10 0.1357332887 62.7635991463) (40 . 0.0000000000) (41 . 0.0000000000) (42 . 0.0000000000) (91 . 0) (10 -4.8199556166 62.2213902421) (40 . 0.0000000000) (41 . 0.0000000000) (42 . 0.5564744024) (91 . 0) (10 -5.5421111679 61.7734539620) (40 . 0.0000000000) (41 . 0.0000000000) (42 . 0.0000000000) (91 . 0) (10 -5.5421111679 61.8774783772) (40 . 0.0000000000) (41 . 0.0000000000) (42 . 0.2849552790) (91 . 0) (10 -5.4309733884 61.6983038651) (40 . 0.0000000000) (41 . 0.0000000000) (42 . 0.0000000000) (91 . 0) (10 0.1357332882 58.9374763869) (40 . 0.0000000000) (41 . 0.0000000000) (42 . 0.2343570514) (91 . 0) (10 0.5800443913 58.9374763871) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 65) (70 . 0) (43 . 0.0000000000) (38 . 0.0000000000) (39 . 0.0000000000) (10 4.8578888320 67.1313221971) (40 . 0.0000000000) (41 . 0.0000000000) (42 . 0.0000000000) (91 . 0) (10 4.8578888320 66.5967000000) (40 . 0.0000000000) (41 . 0.0000000000) (42 . 0.4142135624) (91 . 0) (10 5.0578888322 66.3967000000) (40 . 0.0000000000) (41 . 0.0000000000) (42 . 0.0000000000) (91 . 0) (10 6.0578888322 66.3967000000) (40 . 0.0000000000) (41 . 0.0000000000) (42 . -0.4142135624) (91 . 0) (10 6.2578888319 66.1967000000) (40 . 0.0000000000) (41 . 0.0000000000) (42 . 0.0000000000) (91 . 0) (10 6.2578888319 64.3779464253) (40 . 0.0000000000) (41 . 0.0000000000) (42 . -0.2849552787) (91 . 0) (10 6.1467510526 64.1987719134) (40 . 0.0000000000) (41 . 0.0000000000) (42 . 0.0000000000) (91 . 0) (10 0.5800443909 61.4379444351) (40 . 0.0000000000) (41 . 0.0000000000) (42 . -0.2343570514) (91 . 0) (10 0.1357332879 61.4379444349) (40 . 0.0000000000) (41 . 0.0000000000) (42 . 0.0000000000) (91 . 0) (10 -5.4309733884 64.1987719129) (40 . 0.0000000000) (41 . 0.0000000000) (42 . -0.2849552790) (91 . 0) (10 -5.5421111679 64.3779464250) (40 . 0.0000000000) (41 . 0.0000000000) (42 . 0.0000000000) (91 . 0) (10 -5.5421111679 66.1967000000) (40 . 0.0000000000) (41 . 0.0000000000) (42 . -0.4142135624) (91 . 0) (10 -5.3421111677 66.3966999999) (40 . 0.0000000000) (41 . 0.0000000000) (42 . 0.0000000000) (91 . 0) (10 -4.3421111677 66.3966999999) (40 . 0.0000000000) (41 . 0.0000000000) (42 . 0.4142135624) (91 . 0) (10 -4.1421111680 66.5967000000) (40 . 0.0000000000) (41 . 0.0000000000) (42 . 0.0000000000) (91 . 0) (10 -4.1421111680 67.1189032619) (40 . 0.0000000000) (41 . 0.0000000000) (42 . 0.1876437528) (91 . 0) (10 -4.1946803399 67.2540481876) (40 . 0.0000000000) (41 . 0.0000000000) (42 . 0.0000000000) (91 . 0) (10 -5.1826606833 68.3318449257) (40 . 0.0000000000) (41 . 0.0000000000) (42 . 0.2102297862) (91 . 0) (10 -5.3300915111 68.3966999999) (40 . 0.0000000000) (41 . 0.0000000000) (42 . 0.0000000000) (91 . 0) (10 -6.9421111678 68.3966999999) (40 . 0.0000000000) (41 . 0.0000000000) (42 . 0.4142135624) (91 . 0) (10 -7.1421111680 68.1967000000) (40 . 0.0000000000) (41 . 0.0000000000) (42 . 0.0000000000) (91 . 0) (10 -7.1421111680 56.5967000000) (40 . 0.0000000000) (41 . 0.0000000000) (42 . 0.4142135624) (91 . 0) (10 -6.9421111678 56.3966999999) (40 . 0.0000000000) (41 . 0.0000000000) (42 . 0.0000000000) (91 . 0) (10 -5.9421111678 56.3966999999) (40 . 0.0000000000) (41 . 0.0000000000) (42 . 0.4142135624) (91 . 0) (10 -5.7421111681 56.5967000000) (40 . 0.0000000000) (41 . 0.0000000000) (42 . 0.0000000000) (91 . 0) (10 -5.7421111681 59.0967000000) (40 . 0.0000000000) (41 . 0.0000000000) (42 . -0.5788431251) (91 . 0) (10 -4.9901756553 59.5285894504) (40 . 0.0000000000) (41 . 0.0000000000) (42 . 0.0000000000) (91 . 0) (10 -4.4199556161 59.2457868447) (40 . 0.0000000000) (41 . 0.0000000000) (42 . -0.2849552788) (91 . 0) (10 -4.1421111680 58.7978505647) (40 . 0.0000000000) (41 . 0.0000000000) (42 . 0.0000000000) (91 . 0) (10 -4.1421111680 54.3533563146) (40 . 0.0000000000) (41 . 0.0000000000) (42 . -0.2840790438) (91 . 0) (10 -4.2526684489 54.1744708764) (40 . 0.0000000000) (41 . 0.0000000000) (42 . 0.0000000000) (91 . 0) (10 -4.4315538869 54.0850281572) (40 . 0.0000000000) (41 . 0.0000000000) (42 . 0.4142135624) (91 . 0) (10 -4.5209966062 53.8167000000) (40 . 0.0000000000) (41 . 0.0000000000) (42 . 0.0000000000) (91 . 0) (10 -3.9162752462 52.6072572809) (40 . 0.0000000000) (41 . 0.0000000000) (42 . 0.2840790438) (91 . 0) (10 -3.7373898082 52.4967000000) (40 . 0.0000000000) (41 . 0.0000000000) (42 . 0.0000000000) (91 . 0) (10 -3.0609966062 52.4967000000) (40 . 0.0000000000) (41 . 0.0000000000) (42 . 0.4142135624) (91 . 0) (10 -2.8609966060 52.6967000000) (40 . 0.0000000000) (41 . 0.0000000000) (42 . 0.0000000000) (91 . 0) (10 -2.8609966060 57.9432778508) (40 . 0.0000000000) (41 . 0.0000000000) (42 . -0.5564744024) (91 . 0) (10 -2.1388410548 58.3912141310) (40 . 0.0000000000) (41 . 0.0000000000) (42 . 0.0000000000) (91 . 0) (10 0.2690266202 57.1970238086) (40 . 0.0000000000) (41 . 0.0000000000) (42 . 0.2343570514) (91 . 0) (10 0.4467510614 57.1970238087) (40 . 0.0000000000) (41 . 0.0000000000) (42 . 0.0000000000) (91 . 0) (10 2.8546187183 58.3912141254) (40 . 0.0000000000) (41 . 0.0000000000) (42 . -0.5564744028) (91 . 0) (10 3.5767742701 57.9432778455) (40 . 0.0000000000) (41 . 0.0000000000) (42 . 0.0000000000) (91 . 0) (10 3.5767742701 52.6967000000) (40 . 0.0000000000) (41 . 0.0000000000) (42 . 0.4142135624) (91 . 0) (10 3.7767742703 52.4967000000) (40 . 0.0000000000) (41 . 0.0000000000) (42 . 0.0000000000) (91 . 0) (10 4.4531674728 52.4967000000) (40 . 0.0000000000) (41 . 0.0000000000) (42 . 0.2840790438) (91 . 0) (10 4.6320529108 52.6072572809) (40 . 0.0000000000) (41 . 0.0000000000) (42 . 0.0000000000) (91 . 0) (10 5.2367742702 53.8167000000) (40 . 0.0000000000) (41 . 0.0000000000) (42 . 0.4142135624) (91 . 0) (10 5.1473315514 54.0850281573) (40 . 0.0000000000) (41 . 0.0000000000) (42 . 0.0000000000) (91 . 0) (10 4.9684461130 54.1744708764) (40 . 0.0000000000) (41 . 0.0000000000) (42 . -0.2840790438) (91 . 0) (10 4.8578888320 54.3533563146) (40 . 0.0000000000) (41 . 0.0000000000) (42 . 0.0000000000) (91 . 0) (10 4.8578888320 58.7978505647) (40 . 0.0000000000) (41 . 0.0000000000) (42 . -0.2849552788) (91 . 0) (10 5.1357332806 59.2457868447) (40 . 0.0000000000) (41 . 0.0000000000) (42 . 0.0000000000) (91 . 0) (10 5.7059533194 59.5285894504) (40 . 0.0000000000) (41 . 0.0000000000) (42 . -0.5788431251) (91 . 0) (10 6.4578888321 59.0967000000) (40 . 0.0000000000) (41 . 0.0000000000) (42 . 0.0000000000) (91 . 0) (10 6.4578888321 56.5967000000) (40 . 0.0000000000) (41 . 0.0000000000) (42 . 0.4142135624) (91 . 0) (10 6.6578888323 56.3967000000) (40 . 0.0000000000) (41 . 0.0000000000) (42 . 0.0000000000) (91 . 0) (10 7.6578888323 56.3967000000) (40 . 0.0000000000) (41 . 0.0000000000) (42 . 0.4142135624) (91 . 0) (10 7.8578888320 56.5967000000) (40 . 0.0000000000) (41 . 0.0000000000) (42 . 0.0000000000) (91 . 0) (10 7.8578888320 68.1967000000) (40 . 0.0000000000) (41 . 0.0000000000) (42 . 0.4142135624) (91 . 0) (10 7.6578888323 68.3967000000) (40 . 0.0000000000) (41 . 0.0000000000) (42 . 0.0000000000) (91 . 0) (10 6.0454832279 68.3966999999) (40 . 0.0000000000) (41 . 0.0000000000) (42 . 0.2102297862) (91 . 0) (10 5.8980524000 68.3318449257) (40 . 0.0000000000) (41 . 0.0000000000) (42 . 0.0000000000) (91 . 0) (10 4.9100720566 67.2540481876) (40 . 0.0000000000) (41 . 0.0000000000) (42 . 0.1876437528) (91 . 0) (10 4.8575028848 67.1189032619) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 80) (70 . 1) (43 . 0.0000000000) (38 . 0.0000000000) (39 . 0.0000000000) (10 -20.9421111602 72.8967000000) (40 . 0.0000000000) (41 . 0.0000000000) (42 . 0.4142135624) (91 . 0) (10 -21.4421111602 73.3967000000) (40 . 0.0000000000) (41 . 0.0000000000) (42 . 0.0000000000) (91 . 0) (10 -28.0421111602 73.3967000000) (40 . 0.0000000000) (41 . 0.0000000000) (42 . -0.4142135624) (91 . 0) (10 -28.5421111602 73.8967000000) (40 . 0.0000000000) (41 . 0.0000000000) (42 . 0.0000000000) (91 . 0) (10 -28.5421111602 77.8967000000) (40 . 0.0000000000) (41 . 0.0000000000) (42 . 0.4142135624) (91 . 0) (10 -29.0421111602 78.3967000000) (40 . 0.0000000000) (41 . 0.0000000000) (42 . 0.0000000000) (91 . 0) (10 -29.3405054536 78.3967000000) (40 . 0.0000000000) (41 . 0.0000000000) (42 . 0.3152987889) (91 . 0) (10 -29.8103517640 78.0677100716) (40 . 0.0000000000) (41 . 0.0000000000) (42 . 0.0000000000) (91 . 0) (10 -30.4300496843 76.3651040286) (40 . 0.0000000000) (41 . 0.0000000000) (42 . 0.5205670506) (91 . 0) (10 -30.2421111602 76.0967000000) (40 . 0.0000000000) (41 . 0.0000000000) (42 . 0.0000000000) (91 . 0) (10 -30.0421111602 76.0967000000) (40 . 0.0000000000) (41 . 0.0000000000) (42 . -0.4142135624) (91 . 0) (10 -29.7421111602 75.7967000000) (40 . 0.0000000000) (41 . 0.0000000000) (42 . 0.0000000000) (91 . 0) (10 -29.7421111602 73.8967000000) (40 . 0.0000000000) (41 . 0.0000000000) (42 . -0.4142135624) (91 . 0) (10 -30.2421111602 73.3967000000) (40 . 0.0000000000) (41 . 0.0000000000) (42 . 0.0000000000) (91 . 0) (10 -30.4421111602 73.3967000000) (40 . 0.0000000000) (41 . 0.0000000000) (42 . 0.4142135624) (91 . 0) (10 -30.9421111602 72.8967000000) (40 . 0.0000000000) (41 . 0.0000000000) (42 . 0.0000000000) (91 . 0) (10 -30.9421111602 68.8967000000) (40 . 0.0000000000) (41 . 0.0000000000) (42 . 0.4142135624) (91 . 0) (10 -30.4421111602 68.3967000000) (40 . 0.0000000000) (41 . 0.0000000000) (42 . 0.0000000000) (91 . 0) (10 -27.6421111602 68.3967000000) (40 . 0.0000000000) (41 . 0.0000000000) (42 . 0.4142135624) (91 . 0) (10 -27.1421111602 68.8967000000) (40 . 0.0000000000) (41 . 0.0000000000) (42 . 0.0000000000) (91 . 0) (10 -27.1421111602 69.0967000000) (40 . 0.0000000000) (41 . 0.0000000000) (42 . 0.4142135624) (91 . 0) (10 -27.6421111602 69.5967000000) (40 . 0.0000000000) (41 . 0.0000000000) (42 . 0.0000000000) (91 . 0) (10 -28.0421111602 69.5967000000) (40 . 0.0000000000) (41 . 0.0000000000) (42 . -0.4142135624) (91 . 0) (10 -28.5421111602 70.0967000000) (40 . 0.0000000000) (41 . 0.0000000000) (42 . 0.0000000000) (91 . 0) (10 -28.5421111602 70.7967000000) (40 . 0.0000000000) (41 . 0.0000000000) (42 . -0.4142135624) (91 . 0) (10 -28.0421111602 71.2967000000) (40 . 0.0000000000) (41 . 0.0000000000) (42 . 0.0000000000) (91 . 0) (10 -23.8421111602 71.2967000000) (40 . 0.0000000000) (41 . 0.0000000000) (42 . -0.4142135624) (91 . 0) (10 -23.3421111602 70.7967000000) (40 . 0.0000000000) (41 . 0.0000000000) (42 . 0.0000000000) (91 . 0) (10 -23.3421111602 70.0967000000) (40 . 0.0000000000) (41 . 0.0000000000) (42 . -0.4142135624) (91 . 0) (10 -23.8421111602 69.5967000000) (40 . 0.0000000000) (41 . 0.0000000000) (42 . 0.0000000000) (91 . 0) (10 -24.2421111602 69.5967000000) (40 . 0.0000000000) (41 . 0.0000000000) (42 . 0.4142135624) (91 . 0) (10 -24.7421111602 69.0967000000) (40 . 0.0000000000) (41 . 0.0000000000) (42 . 0.0000000000) (91 . 0) (10 -24.7421111602 68.8967000000) (40 . 0.0000000000) (41 . 0.0000000000) (42 . 0.4142135624) (91 . 0) (10 -24.2421111602 68.3967000000) (40 . 0.0000000000) (41 . 0.0000000000) (42 . 0.0000000000) (91 . 0) (10 0.3578888398 68.3967000000) (40 . 0.0000000000) (41 . 0.0000000000) (42 . 0.0000000000) (91 . 0) (10 24.9578888398 68.3967000000) (40 . 0.0000000000) (41 . 0.0000000000) (42 . 0.4142135624) (91 . 0) (10 25.4578888398 68.8967000000) (40 . 0.0000000000) (41 . 0.0000000000) (42 . 0.0000000000) (91 . 0) (10 25.4578888398 69.0967000000) (40 . 0.0000000000) (41 . 0.0000000000) (42 . 0.4142135624) (91 . 0) (10 24.9578888398 69.5967000000) (40 . 0.0000000000) (41 . 0.0000000000) (42 . 0.0000000000) (91 . 0) (10 24.5578888398 69.5967000000) (40 . 0.0000000000) (41 . 0.0000000000) (42 . -0.4142135624) (91 . 0) (10 24.0578888398 70.0967000000) (40 . 0.0000000000) (41 . 0.0000000000) (42 . 0.0000000000) (91 . 0) (10 24.0578888398 70.7967000000) (40 . 0.0000000000) (41 . 0.0000000000) (42 . -0.4142135624) (91 . 0) (10 24.5578888398 71.2967000000) (40 . 0.0000000000) (41 . 0.0000000000) (42 . 0.0000000000) (91 . 0) (10 28.7578888398 71.2967000000) (40 . 0.0000000000) (41 . 0.0000000000) (42 . -0.4142135624) (91 . 0) (10 29.2578888398 70.7967000000) (40 . 0.0000000000) (41 . 0.0000000000) (42 . 0.0000000000) (91 . 0) (10 29.2578888398 70.0967000000) (40 . 0.0000000000) (41 . 0.0000000000) (42 . -0.4142135624) (91 . 0) (10 28.7578888398 69.5967000000) (40 . 0.0000000000) (41 . 0.0000000000) (42 . 0.0000000000) (91 . 0) (10 28.3578888398 69.5967000000) (40 . 0.0000000000) (41 . 0.0000000000) (42 . 0.4142135624) (91 . 0) (10 27.8578888398 69.0967000000) (40 . 0.0000000000) (41 . 0.0000000000) (42 . 0.0000000000) (91 . 0) (10 27.8578888398 68.8967000000) (40 . 0.0000000000) (41 . 0.0000000000) (42 . 0.4142135624) (91 . 0) (10 28.3578888398 68.3967000000) (40 . 0.0000000000) (41 . 0.0000000000) (42 . 0.0000000000) (91 . 0) (10 31.1578888398 68.3967000000) (40 . 0.0000000000) (41 . 0.0000000000) (42 . 0.4142135624) (91 . 0) (10 31.6578888398 68.8967000000) (40 . 0.0000000000) (41 . 0.0000000000) (42 . 0.0000000000) (91 . 0) (10 31.6578888398 72.8967000000) (40 . 0.0000000000) (41 . 0.0000000000) (42 . 0.4142135624) (91 . 0) (10 31.1578888398 73.3967000000) (40 . 0.0000000000) (41 . 0.0000000000) (42 . 0.0000000000) (91 . 0) (10 30.9578888398 73.3967000000) (40 . 0.0000000000) (41 . 0.0000000000) (42 . -0.4142135624) (91 . 0) (10 30.4578888398 73.8967000000) (40 . 0.0000000000) (41 . 0.0000000000) (42 . 0.0000000000) (91 . 0) (10 30.4578888398 75.7967000000) (40 . 0.0000000000) (41 . 0.0000000000) (42 . -0.4142135624) (91 . 0) (10 30.7578888398 76.0967000000) (40 . 0.0000000000) (41 . 0.0000000000) (42 . 0.0000000000) (91 . 0) (10 30.9578888398 76.0967000000) (40 . 0.0000000000) (41 . 0.0000000000) (42 . 0.5205670506) (91 . 0) (10 31.1458273640 76.3651040286) (40 . 0.0000000000) (41 . 0.0000000000) (42 . 0.0000000000) (91 . 0) (10 30.5261294436 78.0677100716) (40 . 0.0000000000) (41 . 0.0000000000) (42 . 0.3152987889) (91 . 0) (10 30.0562831332 78.3967000000) (40 . 0.0000000000) (41 . 0.0000000000) (42 . 0.0000000000) (91 . 0) (10 29.7578888398 78.3967000000) (40 . 0.0000000000) (41 . 0.0000000000) (42 . 0.4142135624) (91 . 0) (10 29.2578888398 77.8967000000) (40 . 0.0000000000) (41 . 0.0000000000) (42 . 0.0000000000) (91 . 0) (10 29.2578888398 73.8967000000) (40 . 0.0000000000) (41 . 0.0000000000) (42 . -0.4142135624) (91 . 0) (10 28.7578888398 73.3967000000) (40 . 0.0000000000) (41 . 0.0000000000) (42 . 0.0000000000) (91 . 0) (10 22.1578888398 73.3967000000) (40 . 0.0000000000) (41 . 0.0000000000) (42 . 0.4142135624) (91 . 0) (10 21.6578888398 72.8967000000) (40 . 0.0000000000) (41 . 0.0000000000) (42 . 0.0000000000) (91 . 0) (10 21.6578888398 71.8967000000) (40 . 0.0000000000) (41 . 0.0000000000) (42 . -0.4142135624) (91 . 0) (10 21.1578888398 71.3967000000) (40 . 0.0000000000) (41 . 0.0000000000) (42 . 0.0000000000) (91 . 0) (10 1.0235742648 71.3967000000) (40 . 0.0000000000) (41 . 0.0000000000) (42 . 0.1989123674) (91 . 0) (10 0.8821529085 71.3381213562) (40 . 0.0000000000) (41 . 0.0000000000) (42 . 0.0000000000) (91 . 0) (10 0.4993101960 70.9552786438) (40 . 0.0000000000) (41 . 0.0000000000) (42 . -0.1989123674) (91 . 0) (10 0.3578888398 70.8967000000) (40 . 0.0000000000) (41 . 0.0000000000) (42 . -0.1989123674) (91 . 0) (10 0.2164674836 70.9552786438) (40 . 0.0000000000) (41 . 0.0000000000) (42 . 0.0000000000) (91 . 0) (10 -0.1663752289 71.3381213562) (40 . 0.0000000000) (41 . 0.0000000000) (42 . 0.1989123674) (91 . 0) (10 -0.3077965851 71.3967000000) (40 . 0.0000000000) (41 . 0.0000000000) (42 . 0.0000000000) (91 . 0) (10 -20.4421111602 71.3967000000) (40 . 0.0000000000) (41 . 0.0000000000) (42 . -0.4142135624) (91 . 0) (10 -20.9421111602 71.8967000000) (40 . 0.0000000000) (41 . 0.0000000000) (42 . 0.0000000000) (91 . 0) (210 0.0000000000 0.0000000000 1.0000000000))
((0 . "LWPOLYLINE") (100 . "AcDbEntity") (67 . 0) (8 . "A-Window") (62 . 3) (6 . "Continuous") (100 . "AcDbPolyline") (90 . 44) (70 . 1) (43 . 0.0000000000) (38 . 0.0000000000) (39 . 0.0000000000) (10 23.6421111610 70.2966877930) (40 . 0.0000000000) (41 . 0.0000000000) (42 . 0.0000000000) (91 . 0) (10 23.6421111610 70.0967122070) (40 . 0.0000000000) (41 . 0.0000000000) (42 . 0.4142225008) (91 . 0) (10 24.0421111608 69.6967000000) (40 . 0.0000000000) (41 . 0.0000000000) (42 . 0.0000000000) (91 . 0) (10 24.2421111608 69.6967000000) (40 . 0.0000000000) (41 . 0.0000000000) (42 . -0.4142135624) (91 . 0) (10 24.8421111608 69.0967000000) (40 . 0.0000000000) (41 . 0.0000000000) (42 . 0.0000000000) (91 . 0) (10 24.8421111608 68.8967000000) (40 . 0.0000000000) (41 . 0.0000000000) (42 . -0.2513806714) (91 . 0) (10 24.5737736398 68.3967000000) (40 . 0.0000000000) (41 . 0.0000000000) (42 . 0.0000000000) (91 . 0) (10 22.8419369362 68.3967000000) (40 . 0.0000000000) (41 . 0.0000000000) (42 . 0.4142135624) (91 . 0) (10 22.3419369362 67.8967000000) (40 . 0.0000000000) (41 . 0.0000000000) (42 . 0.0000000000) (91 . 0) (10 22.3419369362 63.2967000000) (40 . 0.0000000000) (41 . 0.0000000000) (42 . 0.4142135624) (91 . 0) (10 22.8419369362 62.7967000000) (40 . 0.0000000000) (41 . 0.0000000000) (42 . 0.0000000000) (91 . 0) (10 23.0521408922 62.7967000000) (40 . 0.0000000000) (41 . 0.0000000000) (42 . 0.0000000000) (91 . 0) (10 23.1968257876 63.1989988506) (40 . 0.0000000000) (41 . 0.0000000000) (42 . 0.0000000000) (91 . 0) (10 23.5540632006 63.1989988506) (40 . 0.0000000000) (41 . 0.0000000000) (42 . 0.0000000000) (91 . 0) (10 23.6938075589 62.7967000000) (40 . 0.0000000000) (41 . 0.0000000000) (42 . 0.0000000000) (91 . 0) (10 24.3354742255 62.7967000000) (40 . 0.0000000000) (41 . 0.0000000000) (42 . 0.0000000000) (91 . 0) (10 24.4801591210 63.1989988506) (40 . 0.0000000000) (41 . 0.0000000000) (42 . 0.0000000000) (91 . 0) (10 24.8373965339 63.1989988506) (40 . 0.0000000000) (41 . 0.0000000000) (42 . 0.0000000000) (91 . 0) (10 24.9771408922 62.7967000000) (40 . 0.0000000000) (41 . 0.0000000000) (42 . 0.0000000000) (91 . 0) (10 25.6188075589 62.7967000000) (40 . 0.0000000000) (41 . 0.0000000000) (42 . 0.0000000000) (91 . 0) (10 25.7634924543 63.1989988506) (40 . 0.0000000000) (41 . 0.0000000000) (42 . 0.0000000000) (91 . 0) (10 26.1207298673 63.1989988506) (40 . 0.0000000000) (41 . 0.0000000000) (42 . 0.0000000000) (91 . 0) (10 26.2604742255 62.7967000000) (40 . 0.0000000000) (41 . 0.0000000000) (42 . 0.0000000000) (91 . 0) (10 26.9021408922 62.7967000000) (40 . 0.0000000000) (41 . 0.0000000000) (42 . 0.0000000000) (91 . 0) (10 27.0468257876 63.1989988506) (40 . 0.0000000000) (41 . 0.0000000000) (42 . 0.0000000000) (91 . 0) (10 27.4040632006 63.1989988506) (40 . 0.0000000000) (41 . 0.0000000000) (42 . 0.0000000000) (91 . 0) (10 27.5438075589 62.7967000000) (40 . 0.0000000000) (41 . 0.0000000000) (42 . 0.0000000000) (91 . 0) (10 28.1854742255 62.7967000000) (40 . 0.0000000000) (41 . 0.0000000000) (42 . 0.0000000000) (91 . 0) (10 28.3301591210 63.1989988506) (40 . 0.0000000000) (41 . 0.0000000000) (42 . 0.0000000000) (91 . 0) (10 28.6873965339 63.1989988506) (40 . 0.0000000000) (41 . 0.0000000000) (42 . 0.0000000000) (91 . 0) (10 28.8271408922 62.7967000000) (40 . 0.0000000000) (41 . 0.0000000000) (42 . 0.0000000000) (91 . 0) (10 29.0419369361 62.7967000000) (40 . 0.0000000000) (41 . 0.0000000000) (42 . 0.4142135624) (91 . 0) (10 29.5419369361 63.2967000000) (40 . 0.0000000000) (41 . 0.0000000000) (42 . 0.0000000000) (91 . 0) (10 29.5419369361 67.8967000000) (40 . 0.0000000000) (41 . 0.0000000000) (42 . 0.4142135624) (91 . 0) (10 29.0419369361 68.3967000000) (40 . 0.0000000000) (41 . 0.0000000000) (42 . 0.0000000000) (91 . 0) (10 27.3104486818 68.3967000000) (40 . 0.0000000000) (41 . 0.0000000000) (42 . -0.2513806714) (91 . 0) (10 27.0421111608 68.8967000000) (40 . 0.0000000000) (41 . 0.0000000000) (42 . 0.0000000000) (91 . 0) (10 27.0421111608 69.0967000000) (40 . 0.0000000000) (41 . 0.0000000000) (42 . -0.4142135624) (91 . 0) (10 27.6421111608 69.6967000000) (40 . 0.0000000000) (41 . 0.0000000000) (42 . 0.0000000000) (91 . 0) (10 27.8421111608 69.6967000000) (40 . 0.0000000000) (41 . 0.0000000000) (42 . 0.4142135624) (91 . 0) (10 28.2421111608 70.0967000000) (40 . 0.0000000000) (41 . 0.0000000000) (42 . 0.0000000000) (91 . 0) (10 28.2421111608 70.2967000000) (40 . 0.0000000000) (41 . 0.0000000000) (42 . 0.4142135624) (91 . 0) (10 27.8421111608 70.6967000000) (40 . 0.0000000000) (41 . 0.0000000000) (42 . 0.0000000000) (91 . 0) (10 24.0421111608 70.6967000000) (40 . 0.0000000000) (41 . 0.0000000000) (42 . 0.4142225008) (91 . 0) (210 0.0000000000 0.0000000000 -1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 28.0969369362 67.3467000000) (40 . 0.0000000000) (41 . 0.0000000000) (42 . 0.0000000000) (91 . 0) (10 28.0969369362 64.2467000000) (40 . 0.0000000000) (41 . 0.0000000000) (42 . 0.0000000000) (91 . 0) (10 26.5969369362 64.2467000000) (40 . 0.0000000000) (41 . 0.0000000000) (42 . 0.0000000000) (91 . 0) (10 26.5969369362 67.3467000000) (40 . 0.0000000000) (41 . 0.0000000000) (42 . 0.0000000000) (91 . 0) (210 0.0000000000 0.0000000000 -1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 25.2469369362 67.3467000000) (40 . 0.0000000000) (41 . 0.0000000000) (42 . 0.0000000000) (91 . 0) (10 25.2469369362 64.2467000000) (40 . 0.0000000000) (41 . 0.0000000000) (42 . 0.0000000000) (91 . 0) (10 23.7469369362 64.2467000000) (40 . 0.0000000000) (41 . 0.0000000000) (42 . 0.0000000000) (91 . 0) (10 23.7469369362 67.3467000000) (40 . 0.0000000000) (41 . 0.0000000000) (42 . 0.0000000000) (91 . 0) (210 0.0000000000 0.0000000000 -1.0000000000))
((0 . "LWPOLYLINE") (100 . "AcDbEntity") (67 . 0) (8 . "A-Window") (62 . 151) (6 . "Continuous") (100 . "AcDbPolyline") (90 . 44) (70 . 1) (43 . 0.0000000000) (38 . 0.0000000000) (39 . 0.0000000000) (10 31.6578888398 91.8967000000) (40 . 0.0000000000) (41 . 0.0000000000) (42 . 0.0000000000) (91 . 0) (10 31.6578888398 80.7967000000) (40 . 0.0000000000) (41 . 0.0000000000) (42 . -0.4142135624) (91 . 0) (10 31.1578888398 80.2967000000) (40 . 0.0000000000) (41 . 0.0000000000) (42 . 0.0000000000) (91 . 0) (10 29.1578888398 80.2967000000) (40 . 0.0000000000) (41 . 0.0000000000) (42 . 0.4142135624) (91 . 0) (10 28.6578888398 79.7967000000) (40 . 0.0000000000) (41 . 0.0000000000) (42 . 0.0000000000) (91 . 0) (10 28.6578888398 79.5967000000) (40 . 0.0000000000) (41 . 0.0000000000) (42 . 0.4142135624) (91 . 0) (10 29.1578888398 79.0967000000) (40 . 0.0000000000) (41 . 0.0000000000) (42 . 0.0000000000) (91 . 0) (10 31.1578888398 79.0967000000) (40 . 0.0000000000) (41 . 0.0000000000) (42 . -0.4142135624) (91 . 0) (10 31.6578888398 78.5967000000) (40 . 0.0000000000) (41 . 0.0000000000) (42 . 0.0000000000) (91 . 0) (10 31.6578888398 76.2967000000) (40 . 0.0000000000) (41 . 0.0000000000) (42 . -0.4142135624) (91 . 0) (10 31.4578888398 76.0967000000) (40 . 0.0000000000) (41 . 0.0000000000) (42 . 0.0000000000) (91 . 0) (10 30.7757356338 76.0967000000) (40 . 0.0000000000) (41 . 0.0000000000) (42 . 0.5522631265) (91 . 0) (10 30.5954310223 75.8101537865) (40 . 0.0000000000) (41 . 0.0000000000) (42 . 0.0000000000) (91 . 0) (10 31.6381934513 73.6377320594) (40 . 0.0000000000) (41 . 0.0000000000) (42 . -0.1123491485) (91 . 0) (10 31.6578888398 73.5511858458) (40 . 0.0000000000) (41 . 0.0000000000) (42 . 0.0000000000) (91 . 0) (10 31.6578888398 67.1967000000) (40 . 0.0000000000) (41 . 0.0000000000) (42 . 0.4142135624) (91 . 0) (10 32.2578888398 66.5967000000) (40 . 0.0000000000) (41 . 0.0000000000) (42 . 0.4142135624) (91 . 0) (10 32.8578888398 67.1967000000) (40 . 0.0000000000) (41 . 0.0000000000) (42 . 0.0000000000) (91 . 0) (10 32.8578888398 93.0967000000) (40 . 0.0000000000) (41 . 0.0000000000) (42 . 0.4142135624) (91 . 0) (10 32.3578888398 93.5967000000) (40 . 0.0000000000) (41 . 0.0000000000) (42 . 0.0000000000) (91 . 0) (10 0.3578888398 93.5967000000) (40 . 0.0000000000) (41 . 0.0000000000) (42 . 0.0000000000) (91 . 0) (10 -31.6421111602 93.5967000000) (40 . 0.0000000000) (41 . 0.0000000000) (42 . 0.4142135624) (91 . 0) (10 -32.1421111602 93.0967000000) (40 . 0.0000000000) (41 . 0.0000000000) (42 . 0.0000000000) (91 . 0) (10 -32.1421111602 67.1967000000) (40 . 0.0000000000) (41 . 0.0000000000) (42 . 0.4142135624) (91 . 0) (10 -31.5421111602 66.5967000000) (40 . 0.0000000000) (41 . 0.0000000000) (42 . 0.4142135624) (91 . 0) (10 -30.9421111602 67.1967000000) (40 . 0.0000000000) (41 . 0.0000000000) (42 . 0.0000000000) (91 . 0) (10 -30.9421111602 73.5511858458) (40 . 0.0000000000) (41 . 0.0000000000) (42 . -0.1123491485) (91 . 0) (10 -30.9224157717 73.6377320594) (40 . 0.0000000000) (41 . 0.0000000000) (42 . 0.0000000000) (91 . 0) (10 -29.8796533427 75.8101537865) (40 . 0.0000000000) (41 . 0.0000000000) (42 . 0.5522631265) (91 . 0) (10 -30.0599579542 76.0967000000) (40 . 0.0000000000) (41 . 0.0000000000) (42 . 0.0000000000) (91 . 0) (10 -30.7421111602 76.0967000000) (40 . 0.0000000000) (41 . 0.0000000000) (42 . -0.4142135624) (91 . 0) (10 -30.9421111602 76.2967000000) (40 . 0.0000000000) (41 . 0.0000000000) (42 . 0.0000000000) (91 . 0) (10 -30.9421111602 78.5967000000) (40 . 0.0000000000) (41 . 0.0000000000) (42 . -0.4142135624) (91 . 0) (10 -30.4421111602 79.0967000000) (40 . 0.0000000000) (41 . 0.0000000000) (42 . 0.0000000000) (91 . 0) (10 -28.4421111602 79.0967000000) (40 . 0.0000000000) (41 . 0.0000000000) (42 . 0.4142135624) (91 . 0) (10 -27.9421111602 79.5967000000) (40 . 0.0000000000) (41 . 0.0000000000) (42 . 0.0000000000) (91 . 0) (10 -27.9421111602 79.7967000000) (40 . 0.0000000000) (41 . 0.0000000000) (42 . 0.4142135624) (91 . 0) (10 -28.4421111602 80.2967000000) (40 . 0.0000000000) (41 . 0.0000000000) (42 . 0.0000000000) (91 . 0) (10 -30.4421111602 80.2967000000) (40 . 0.0000000000) (41 . 0.0000000000) (42 . -0.4142135624) (91 . 0) (10 -30.9421111602 80.7967000000) (40 . 0.0000000000) (41 . 0.0000000000) (42 . 0.0000000000) (91 . 0) (10 -30.9421111602 91.8967000000) (40 . 0.0000000000) (41 . 0.0000000000) (42 . -0.4142135624) (91 . 0) (10 -30.4421111602 92.3967000000) (40 . 0.0000000000) (41 . 0.0000000000) (42 . 0.0000000000) (91 . 0) (10 0.3578888398 92.3967000000) (40 . 0.0000000000) (41 . 0.0000000000) (42 . 0.0000000000) (91 . 0) (10 31.1578888398 92.3967000000) (40 . 0.0000000000) (41 . 0.0000000000) (42 . -0.4142135624) (91 . 0) (210 0.0000000000 0.0000000000 1.0000000000))
((0 . "LINE") (100 . "AcDbEntity") (67 . 0) (8 . "A-Window") (62 . 151) (6 . "Continuous") (100 . "AcDbLine") (10 2.5828888395 59.8994120805 0.0000000000) (11 2.5828888395 60.7929549452 0.0000000000) (210 0.0000000000 0.0000000000 1.0000000000))
((0 . "LINE") (100 . "AcDbEntity") (67 . 0) (8 . "A-Window") (62 . 151) (6 . "Continuous") (100 . "AcDbLine") (10 2.5828888395 61.5694120805 0.0000000000) (11 2.5828888395 62.4629549452 0.0000000000) (210 0.0000000000 0.0000000000 1.0000000000))
((0 . "LINE") (100 . "AcDbEntity") (67 . 0) (8 . "A-Window") (62 . 151) (6 . "Continuous") (100 . "AcDbLine") (10 2.5828888395 56.5594120805 0.0000000000) (11 2.5828888395 57.4529549452 0.0000000000) (210 0.0000000000 0.0000000000 1.0000000000))
((0 . "LINE") (100 . "AcDbEntity") (67 . 0) (8 . "A-Window") (62 . 151) (6 . "Continuous") (100 . "AcDbLine") (10 2.5828888395 58.2294120805 0.0000000000) (11 2.5828888395 59.1229549452 0.0000000000) (210 0.0000000000 0.0000000000 1.0000000000))
((0 . "LINE") (100 . "AcDbEntity") (67 . 0) (8 . "A-Window") (62 . 151) (6 . "Continuous") (100 . "AcDbLine") (10 -1.8671111605 55.5896136866 0.0000000000) (11 -1.8671111605 56.4831565513 0.0000000000) (210 0.0000000000 0.0000000000 1.0000000000))
((0 . "LINE") (100 . "AcDbEntity") (67 . 0) (8 . "A-Window") (62 . 151) (6 . "Continuous") (100 . "AcDbLine") (10 -1.8671111605 57.2596136866 0.0000000000) (11 -1.8671111605 58.1531565513 0.0000000000) (210 0.0000000000 0.0000000000 1.0000000000))
((0 . "LINE") (100 . "AcDbEntity") (67 . 0) (8 . "A-Window") (62 . 151) (6 . "Continuous") (100 . "AcDbLine") (10 -1.8671111605 58.9296136866 0.0000000000) (11 -1.8671111605 59.8231565513 0.0000000000) (210 0.0000000000 0.0000000000 1.0000000000))
((0 . "LINE") (100 . "AcDbEntity") (67 . 0) (8 . "A-Window") (62 . 151) (6 . "Continuous") (100 . "AcDbLine") (10 -1.8671111605 60.5996136866 0.0000000000) (11 -1.8671111605 61.4931565513 0.0000000000) (210 0.0000000000 0.0000000000 1.0000000000))
((0 . "LINE") (100 . "AcDbEntity") (67 . 0) (8 . "A-Window") (62 . 151) (6 . "Continuous") (100 . "AcDbLine") (10 -1.8671111605 62.2696136866 0.0000000000) (11 -1.8671111605 63.1631565513 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 57.2596136866) (40 . 0.0000000000) (41 . 0.0000000000) (42 . 0.0000000000) (91 . 0) (10 -2.3921111605 56.8713851190) (40 . 0.0000000000) (41 . 0.0000000000) (42 . 0.0000000000) (91 . 0) (10 -1.8671111605 56.4831565513) (40 . 0.0000000000) (41 . 0.0000000000) (42 . 0.0000000000) (91 . 0) (10 2.5828888395 57.4529549452) (40 . 0.0000000000) (41 . 0.0000000000) (42 . 0.0000000000) (91 . 0) (10 3.1078888395 57.8411835129) (40 . 0.0000000000) (41 . 0.0000000000) (42 . 0.0000000000) (91 . 0) (10 2.5828888395 58.2294120805) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 60.5996136866) (40 . 0.0000000000) (41 . 0.0000000000) (42 . 0.0000000000) (91 . 0) (10 -2.3921111605 60.2113851190) (40 . 0.0000000000) (41 . 0.0000000000) (42 . 0.0000000000) (91 . 0) (10 -1.8671111605 59.8231565513) (40 . 0.0000000000) (41 . 0.0000000000) (42 . 0.0000000000) (91 . 0) (10 2.5828888395 60.7929549452) (40 . 0.0000000000) (41 . 0.0000000000) (42 . 0.0000000000) (91 . 0) (10 3.1078888395 61.1811835129) (40 . 0.0000000000) (41 . 0.0000000000) (42 . 0.0000000000) (91 . 0) (10 2.5828888395 61.5694120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 3.1078888395 59.5111835129 0.0000000000) (11 -2.3921111605 58.5413851190 0.0000000000) (210 0.0000000000 0.0000000000 1.0000000000))
((0 . "LINE") (100 . "AcDbEntity") (67 . 0) (8 . "A-Window") (62 . 151) (6 . "Continuous") (100 . "AcDbLine") (10 3.1078888395 61.1811835129 0.0000000000) (11 -2.3921111605 60.2113851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 58.9296136866) (40 . 0.0000000000) (41 . 0.0000000000) (42 . 0.0000000000) (91 . 0) (10 -2.3921111605 58.5413851190) (40 . 0.0000000000) (41 . 0.0000000000) (42 . 0.0000000000) (91 . 0) (10 -1.8671111605 58.1531565513) (40 . 0.0000000000) (41 . 0.0000000000) (42 . 0.0000000000) (91 . 0) (10 2.5828888395 59.1229549452) (40 . 0.0000000000) (41 . 0.0000000000) (42 . 0.0000000000) (91 . 0) (10 3.1078888395 59.5111835129) (40 . 0.0000000000) (41 . 0.0000000000) (42 . 0.0000000000) (91 . 0) (10 2.5828888395 59.8994120805) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 62.2696136866) (40 . 0.0000000000) (41 . 0.0000000000) (42 . 0.0000000000) (91 . 0) (10 -2.3921111605 61.8813851190) (40 . 0.0000000000) (41 . 0.0000000000) (42 . 0.0000000000) (91 . 0) (10 -1.8671111605 61.4931565513) (40 . 0.0000000000) (41 . 0.0000000000) (42 . 0.0000000000) (91 . 0) (10 2.5828888395 62.4629549452) (40 . 0.0000000000) (41 . 0.0000000000) (42 . 0.0000000000) (91 . 0) (10 3.1078888395 62.8511835129) (40 . 0.0000000000) (41 . 0.0000000000) (42 . 0.0000000000) (91 . 0) (10 2.5828888395 63.2394120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 3.1078888395 62.8511835129 0.0000000000) (11 -2.3921111605 61.8813851190 0.0000000000) (210 0.0000000000 0.0000000000 1.0000000000))
((0 . "LINE") (100 . "AcDbEntity") (67 . 0) (8 . "A-Window") (62 . 151) (6 . "Continuous") (100 . "AcDbLine") (10 3.1078888395 57.8411835129 0.0000000000) (11 -2.3921111605 56.8713851190 0.0000000000) (210 0.0000000000 0.0000000000 1.0000000000))
((0 . "LINE") (100 . "AcDbEntity") (67 . 0) (8 . "A-Window") (62 . 151) (6 . "Continuous") (100 . "AcDbLine") (10 2.5828888395 66.9194120805 0.0000000000) (11 2.5828888395 67.8129549452 0.0000000000) (210 0.0000000000 0.0000000000 1.0000000000))
((0 . "LINE") (100 . "AcDbEntity") (67 . 0) (8 . "A-Window") (62 . 151) (6 . "Continuous") (100 . "AcDbLine") (10 2.5828888395 61.9094120805 0.0000000000) (11 2.5828888395 62.8029549452 0.0000000000) (210 0.0000000000 0.0000000000 1.0000000000))
((0 . "LINE") (100 . "AcDbEntity") (67 . 0) (8 . "A-Window") (62 . 151) (6 . "Continuous") (100 . "AcDbLine") (10 2.5828888395 63.5794120805 0.0000000000) (11 2.5828888395 64.4729549452 0.0000000000) (210 0.0000000000 0.0000000000 1.0000000000))
((0 . "LINE") (100 . "AcDbEntity") (67 . 0) (8 . "A-Window") (62 . 151) (6 . "Continuous") (100 . "AcDbLine") (10 2.5828888395 65.2494120805 0.0000000000) (11 2.5828888395 66.1429549452 0.0000000000) (210 0.0000000000 0.0000000000 1.0000000000))
((0 . "LINE") (100 . "AcDbEntity") (67 . 0) (8 . "A-Window") (62 . 151) (6 . "Continuous") (100 . "AcDbLine") (10 2.5828888395 71.9294120805 0.0000000000) (11 2.5828888395 72.8229549452 0.0000000000) (210 0.0000000000 0.0000000000 1.0000000000))
((0 . "LINE") (100 . "AcDbEntity") (67 . 0) (8 . "A-Window") (62 . 151) (6 . "Continuous") (100 . "AcDbLine") (10 2.5828888395 70.2594120805 0.0000000000) (11 2.5828888395 71.1529549452 0.0000000000) (210 0.0000000000 0.0000000000 1.0000000000))
((0 . "LINE") (100 . "AcDbEntity") (67 . 0) (8 . "A-Window") (62 . 151) (6 . "Continuous") (100 . "AcDbLine") (10 2.5828888395 68.5894120805 0.0000000000) (11 2.5828888395 69.4829549452 0.0000000000) (210 0.0000000000 0.0000000000 1.0000000000))
((0 . "LINE") (100 . "AcDbEntity") (67 . 0) (8 . "A-Window") (62 . 151) (6 . "Continuous") (100 . "AcDbLine") (10 -1.8671111605 60.9396136866 0.0000000000) (11 -1.8671111605 61.8331565513 0.0000000000) (210 0.0000000000 0.0000000000 1.0000000000))
((0 . "LINE") (100 . "AcDbEntity") (67 . 0) (8 . "A-Window") (62 . 151) (6 . "Continuous") (100 . "AcDbLine") (10 -1.8671111605 65.9496136866 0.0000000000) (11 -1.8671111605 66.8431565513 0.0000000000) (210 0.0000000000 0.0000000000 1.0000000000))
((0 . "LINE") (100 . "AcDbEntity") (67 . 0) (8 . "A-Window") (62 . 151) (6 . "Continuous") (100 . "AcDbLine") (10 -1.8671111605 67.6196136866 0.0000000000) (11 -1.8671111605 68.5131565513 0.0000000000) (210 0.0000000000 0.0000000000 1.0000000000))
((0 . "LINE") (100 . "AcDbEntity") (67 . 0) (8 . "A-Window") (62 . 151) (6 . "Continuous") (100 . "AcDbLine") (10 -1.8671111605 62.6096136866 0.0000000000) (11 -1.8671111605 63.5031565513 0.0000000000) (210 0.0000000000 0.0000000000 1.0000000000))
((0 . "LINE") (100 . "AcDbEntity") (67 . 0) (8 . "A-Window") (62 . 151) (6 . "Continuous") (100 . "AcDbLine") (10 -1.8671111605 64.2796136866 0.0000000000) (11 -1.8671111605 65.1731565513 0.0000000000) (210 0.0000000000 0.0000000000 1.0000000000))
((0 . "LINE") (100 . "AcDbEntity") (67 . 0) (8 . "A-Window") (62 . 151) (6 . "Continuous") (100 . "AcDbLine") (10 -1.8671111605 69.2896136866 0.0000000000) (11 -1.8671111605 70.1831565513 0.0000000000) (210 0.0000000000 0.0000000000 1.0000000000))
((0 . "LINE") (100 . "AcDbEntity") (67 . 0) (8 . "A-Window") (62 . 151) (6 . "Continuous") (100 . "AcDbLine") (10 -1.8671111605 70.9596136866 0.0000000000) (11 -1.8671111605 71.8531565513 0.0000000000) (210 0.0000000000 0.0000000000 1.0000000000))
((0 . "LINE") (100 . "AcDbEntity") (67 . 0) (8 . "A-Window") (62 . 151) (6 . "Continuous") (100 . "AcDbLine") (10 -1.8671111605 72.6296136866 0.0000000000) (11 -1.8671111605 72.8917774718 0.0000000000) (210 0.0000000000 0.0000000000 1.0000000000))
((0 . "LINE") (100 . "AcDbEntity") (67 . 0) (8 . "A-Window") (62 . 151) (6 . "Continuous") (100 . "AcDbLine") (10 3.1078888395 63.1911835129 0.0000000000) (11 -2.3921111605 62.2213851189 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 62.6096136866) (40 . 0.0000000000) (41 . 0.0000000000) (42 . 0.0000000000) (91 . 0) (10 -2.3921111605 62.2213851189) (40 . 0.0000000000) (41 . 0.0000000000) (42 . 0.0000000000) (91 . 0) (10 -1.8671111605 61.8331565513) (40 . 0.0000000000) (41 . 0.0000000000) (42 . 0.0000000000) (91 . 0) (10 2.5828888395 62.8029549452) (40 . 0.0000000000) (41 . 0.0000000000) (42 . 0.0000000000) (91 . 0) (10 3.1078888395 63.1911835129) (40 . 0.0000000000) (41 . 0.0000000000) (42 . 0.0000000000) (91 . 0) (10 2.5828888395 63.5794120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 3.1078888395 64.8611835129 0.0000000000) (11 -2.3921111605 63.8913851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 64.2796136866) (40 . 0.0000000000) (41 . 0.0000000000) (42 . 0.0000000000) (91 . 0) (10 -2.3921111605 63.8913851190) (40 . 0.0000000000) (41 . 0.0000000000) (42 . 0.0000000000) (91 . 0) (10 -1.8671111605 63.5031565513) (40 . 0.0000000000) (41 . 0.0000000000) (42 . 0.0000000000) (91 . 0) (10 2.5828888395 64.4729549452) (40 . 0.0000000000) (41 . 0.0000000000) (42 . 0.0000000000) (91 . 0) (10 3.1078888395 64.8611835129) (40 . 0.0000000000) (41 . 0.0000000000) (42 . 0.0000000000) (91 . 0) (10 2.5828888395 65.2494120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 3.1078888395 66.5311835129 0.0000000000) (11 -2.3921111605 65.5613851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 65.9496136866) (40 . 0.0000000000) (41 . 0.0000000000) (42 . 0.0000000000) (91 . 0) (10 -2.3921111605 65.5613851190) (40 . 0.0000000000) (41 . 0.0000000000) (42 . 0.0000000000) (91 . 0) (10 -1.8671111605 65.1731565513) (40 . 0.0000000000) (41 . 0.0000000000) (42 . 0.0000000000) (91 . 0) (10 2.5828888395 66.1429549452) (40 . 0.0000000000) (41 . 0.0000000000) (42 . 0.0000000000) (91 . 0) (10 3.1078888395 66.5311835129) (40 . 0.0000000000) (41 . 0.0000000000) (42 . 0.0000000000) (91 . 0) (10 2.5828888395 66.9194120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 3.1078888395 68.2011835129 0.0000000000) (11 -2.3921111605 67.2313851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 67.6196136866) (40 . 0.0000000000) (41 . 0.0000000000) (42 . 0.0000000000) (91 . 0) (10 -2.3921111605 67.2313851190) (40 . 0.0000000000) (41 . 0.0000000000) (42 . 0.0000000000) (91 . 0) (10 -1.8671111605 66.8431565513) (40 . 0.0000000000) (41 . 0.0000000000) (42 . 0.0000000000) (91 . 0) (10 2.5828888395 67.8129549452) (40 . 0.0000000000) (41 . 0.0000000000) (42 . 0.0000000000) (91 . 0) (10 3.1078888395 68.2011835129) (40 . 0.0000000000) (41 . 0.0000000000) (42 . 0.0000000000) (91 . 0) (10 2.5828888395 68.5894120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 3.1078888395 69.8711835129 0.0000000000) (11 -2.3921111605 68.9013851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 69.2896136866) (40 . 0.0000000000) (41 . 0.0000000000) (42 . 0.0000000000) (91 . 0) (10 -2.3921111605 68.9013851190) (40 . 0.0000000000) (41 . 0.0000000000) (42 . 0.0000000000) (91 . 0) (10 -1.8671111605 68.5131565513) (40 . 0.0000000000) (41 . 0.0000000000) (42 . 0.0000000000) (91 . 0) (10 2.5828888395 69.4829549452) (40 . 0.0000000000) (41 . 0.0000000000) (42 . 0.0000000000) (91 . 0) (10 3.1078888395 69.8711835129) (40 . 0.0000000000) (41 . 0.0000000000) (42 . 0.0000000000) (91 . 0) (10 2.5828888395 70.2594120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 3.1078888395 71.5411835129 0.0000000000) (11 -2.3921111605 70.5713851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 70.9596136866) (40 . 0.0000000000) (41 . 0.0000000000) (42 . 0.0000000000) (91 . 0) (10 -2.3921111605 70.5713851190) (40 . 0.0000000000) (41 . 0.0000000000) (42 . 0.0000000000) (91 . 0) (10 -1.8671111605 70.1831565513) (40 . 0.0000000000) (41 . 0.0000000000) (42 . 0.0000000000) (91 . 0) (10 2.5828888395 71.1529549452) (40 . 0.0000000000) (41 . 0.0000000000) (42 . 0.0000000000) (91 . 0) (10 3.1078888395 71.5411835129) (40 . 0.0000000000) (41 . 0.0000000000) (42 . 0.0000000000) (91 . 0) (10 2.5828888395 71.9294120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 1.2964471656 72.8917774718 0.0000000000) (11 -2.3921111605 72.2413851190 0.0000000000) (210 0.0000000000 0.0000000000 1.0000000000))
((0 . "LWPOLYLINE") (100 . "AcDbEntity") (67 . 0) (8 . "A-Window") (62 . 151) (6 . "Continuous") (100 . "AcDbPolyline") (90 . 6) (70 . 0) (43 . 0.0000000000) (38 . 0.0000000000) (39 . 0.0000000000) (10 -0.6641509873 72.8917774718) (40 . 0.0000000000) (41 . 0.0000000000) (42 . 0.0000000000) (91 . 0) (10 -1.8671111605 72.6296136866) (40 . 0.0000000000) (41 . 0.0000000000) (42 . 0.0000000000) (91 . 0) (10 -2.3921111605 72.2413851190) (40 . 0.0000000000) (41 . 0.0000000000) (42 . 0.0000000000) (91 . 0) (10 -1.8671111605 71.8531565513) (40 . 0.0000000000) (41 . 0.0000000000) (42 . 0.0000000000) (91 . 0) (10 2.5828888395 72.8229549452) (40 . 0.0000000000) (41 . 0.0000000000) (42 . 0.0000000000) (91 . 0) (10 2.6759572777 72.8917774718) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 4) (70 . 1) (43 . 0.0000000000) (38 . 0.0000000000) (39 . 0.0000000000) (10 5.8578888395 73.8917774718) (40 . 0.0000000000) (41 . 0.0000000000) (42 . 0.0000000000) (91 . 0) (10 5.8578888395 72.8917774718) (40 . 0.0000000000) (41 . 0.0000000000) (42 . 0.0000000000) (91 . 0) (10 -5.1421111605 72.8917774718) (40 . 0.0000000000) (41 . 0.0000000000) (42 . 0.0000000000) (91 . 0) (10 -5.1421111605 73.8917774718) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 3.1078888395 61.5211835128 0.0000000000) (11 -2.3921111605 63.5513851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 60.9396136866) (40 . 0.0000000000) (41 . 0.0000000000) (42 . 0.0000000000) (91 . 0) (10 -2.3921111605 63.5513851190) (40 . 0.0000000000) (41 . 0.0000000000) (42 . 0.0000000000) (91 . 0) (10 -1.8671111605 63.1631565513) (40 . 0.0000000000) (41 . 0.0000000000) (42 . 0.0000000000) (91 . 0) (10 2.5828888395 61.1329549452) (40 . 0.0000000000) (41 . 0.0000000000) (42 . 0.0000000000) (91 . 0) (10 3.1078888395 61.5211835128) (40 . 0.0000000000) (41 . 0.0000000000) (42 . 0.0000000000) (91 . 0) (10 2.5828888395 61.9094120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 2.5828888395 63.2394120805 0.0000000000) (11 2.5828888395 61.1329549452 0.0000000000) (210 0.0000000000 0.0000000000 1.0000000000))
((0 . "LINE") (100 . "AcDbEntity") (67 . 0) (8 . "A-Window") (62 . 151) (6 . "Continuous") (100 . "AcDbLine") (10 3.8219904546 78.2917774718 0.0000000000) (11 -3.1062127756 78.2917774718 0.0000000000) (210 0.0000000000 0.0000000000 1.0000000000))
((0 . "LINE") (100 . "AcDbEntity") (67 . 0) (8 . "A-Window") (62 . 151) (6 . "CENTER2") (100 . "AcDbLine") (10 0.3578888395 37.5451762388 0.0000000000) (11 0.3578888395 81.5869711621 0.0000000000) (210 0.0000000000 0.0000000000 1.0000000000))
((0 . "LINE") (100 . "AcDbEntity") (67 . 0) (8 . "A-Window") (62 . 151) (6 . "Continuous") (100 . "AcDbLine") (10 2.6672899163 77.2917774718 0.0000000000) (11 2.6672899163 73.8917774718 0.0000000000) (210 0.0000000000 0.0000000000 1.0000000000))
((0 . "LINE") (100 . "AcDbEntity") (67 . 0) (8 . "A-Window") (62 . 151) (6 . "Continuous") (100 . "AcDbLine") (10 -1.9515122373 77.2917774718 0.0000000000) (11 -1.9515122373 73.8917774718 0.0000000000) (210 0.0000000000 0.0000000000 1.0000000000))
((0 . "LWPOLYLINE") (100 . "AcDbEntity") (67 . 0) (8 . "A-Window") (62 . 151) (6 . "Continuous") (100 . "AcDbPolyline") (90 . 6) (70 . 0) (43 . 0.0000000000) (38 . 0.0000000000) (39 . 0.0000000000) (10 -4.2609133140 73.8917774718) (40 . 0.0000000000) (41 . 0.0000000000) (42 . 0.0000000000) (91 . 0) (10 -4.2609133140 77.2917774718) (40 . 0.0000000000) (41 . 0.0000000000) (42 . -0.8660254038) (91 . 0) (10 -1.9515122373 77.2917774718) (40 . 0.0000000000) (41 . 0.0000000000) (42 . -0.4330127019) (91 . 0) (10 2.6672899163 77.2917774718) (40 . 0.0000000000) (41 . 0.0000000000) (42 . -0.8660254038) (91 . 0) (10 4.9766909930 77.2917774718) (40 . 0.0000000000) (41 . 0.0000000000) (42 . 0.0000000000) (91 . 0) (10 4.9766909930 73.8917774718) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 4) (70 . 1) (43 . 0.0000000000) (38 . 0.0000000000) (39 . 0.0000000000) (10 2.5828888395 42.6957453328) (40 . 0.0000000000) (41 . 0.0000000000) (42 . 0.0000000000) (91 . 0) (10 0.9713231013 42.5675818646) (40 . 0.0000000000) (41 . 0.0000000000) (42 . 0.0000000000) (91 . 0) (10 2.5828888395 43.0839739004) (40 . 0.0000000000) (41 . 0.0000000000) (42 . 0.0000000000) (91 . 0) (10 2.7903888395 42.8898596166) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 2.7903888395 42.8898596166 0.0000000000) (11 0.9713231013 42.5675818646 0.0000000000) (210 0.0000000000 0.0000000000 1.0000000000))
((0 . "LINE") (100 . "AcDbEntity") (67 . 0) (8 . "A-Window") (62 . 151) (6 . "Continuous") (100 . "AcDbLine") (10 2.5828888395 48.2094120805 0.0000000000) (11 2.5828888395 49.1029549452 0.0000000000) (210 0.0000000000 0.0000000000 1.0000000000))
((0 . "LINE") (100 . "AcDbEntity") (67 . 0) (8 . "A-Window") (62 . 151) (6 . "Continuous") (100 . "AcDbLine") (10 2.5828888395 56.5594120805 0.0000000000) (11 2.5828888395 57.4529549452 0.0000000000) (210 0.0000000000 0.0000000000 1.0000000000))
((0 . "LINE") (100 . "AcDbEntity") (67 . 0) (8 . "A-Window") (62 . 151) (6 . "Continuous") (100 . "AcDbLine") (10 2.8941388395 44.5782406548 0.0000000000) (11 1.6210499782 44.3526917877 0.0000000000) (210 0.0000000000 0.0000000000 1.0000000000))
((0 . "LINE") (100 . "AcDbEntity") (67 . 0) (8 . "A-Window") (62 . 151) (6 . "Continuous") (100 . "AcDbLine") (10 2.5828888395 44.8694120805 0.0000000000) (11 2.5828888395 45.7629549452 0.0000000000) (210 0.0000000000 0.0000000000 1.0000000000))
((0 . "LWPOLYLINE") (100 . "AcDbEntity") (67 . 0) (8 . "A-Window") (62 . 151) (6 . "Continuous") (100 . "AcDbPolyline") (90 . 5) (70 . 0) (43 . 0.0000000000) (38 . 0.0000000000) (39 . 0.0000000000) (10 1.5110249293 44.0504004504) (40 . 0.0000000000) (41 . 0.0000000000) (42 . 0.0000000000) (91 . 0) (10 2.5828888395 44.2870692290) (40 . 0.0000000000) (41 . 0.0000000000) (42 . 0.0000000000) (91 . 0) (10 2.8941388395 44.5782406548) (40 . 0.0000000000) (41 . 0.0000000000) (42 . 0.0000000000) (91 . 0) (10 2.5828888395 44.8694120805) (40 . 0.0000000000) (41 . 0.0000000000) (42 . 0.0000000000) (91 . 0) (10 1.7415027540 44.6836330695) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 2.5828888395 46.5394120805 0.0000000000) (11 2.5828888395 47.4329549452 0.0000000000) (210 0.0000000000 0.0000000000 1.0000000000))
((0 . "LINE") (100 . "AcDbEntity") (67 . 0) (8 . "A-Window") (62 . 151) (6 . "Continuous") (100 . "AcDbLine") (10 2.5828888395 43.0839739004 0.0000000000) (11 2.5828888395 44.2870692290 0.0000000000) (210 0.0000000000 0.0000000000 1.0000000000))
((0 . "LINE") (100 . "AcDbEntity") (67 . 0) (8 . "A-Window") (62 . 151) (6 . "Continuous") (100 . "AcDbLine") (10 -1.8671111605 44.1620742983 0.0000000000) (11 -1.8671111605 44.7931565513 0.0000000000) (210 0.0000000000 0.0000000000 1.0000000000))
((0 . "LINE") (100 . "AcDbEntity") (67 . 0) (8 . "A-Window") (62 . 151) (6 . "Continuous") (100 . "AcDbLine") (10 -1.8671111605 45.5696136866 0.0000000000) (11 -1.8671111605 46.4631565513 0.0000000000) (210 0.0000000000 0.0000000000 1.0000000000))
((0 . "LINE") (100 . "AcDbEntity") (67 . 0) (8 . "A-Window") (62 . 151) (6 . "Continuous") (100 . "AcDbLine") (10 -1.8671111605 47.2396136866 0.0000000000) (11 -1.8671111605 48.1331565513 0.0000000000) (210 0.0000000000 0.0000000000 1.0000000000))
((0 . "LINE") (100 . "AcDbEntity") (67 . 0) (8 . "A-Window") (62 . 151) (6 . "Continuous") (100 . "AcDbLine") (10 -1.8671111605 57.2596136866 0.0000000000) (11 -1.8671111605 58.1531565513 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 45.5696136866) (40 . 0.0000000000) (41 . 0.0000000000) (42 . 0.0000000000) (91 . 0) (10 -2.3921111605 45.1813851190) (40 . 0.0000000000) (41 . 0.0000000000) (42 . 0.0000000000) (91 . 0) (10 -1.8671111605 44.7931565513) (40 . 0.0000000000) (41 . 0.0000000000) (42 . 0.0000000000) (91 . 0) (10 2.5828888395 45.7629549452) (40 . 0.0000000000) (41 . 0.0000000000) (42 . 0.0000000000) (91 . 0) (10 3.1078888395 46.1511835129) (40 . 0.0000000000) (41 . 0.0000000000) (42 . 0.0000000000) (91 . 0) (10 2.5828888395 46.5394120805) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 55.5896136866) (40 . 0.0000000000) (41 . 0.0000000000) (42 . 0.0000000000) (91 . 0) (10 -2.3921111605 55.2013851190) (40 . 0.0000000000) (41 . 0.0000000000) (42 . 0.0000000000) (91 . 0) (10 -1.8671111605 54.8131565513) (40 . 0.0000000000) (41 . 0.0000000000) (42 . 0.0000000000) (91 . 0) (10 2.5828888395 55.7829549452) (40 . 0.0000000000) (41 . 0.0000000000) (42 . 0.0000000000) (91 . 0) (10 3.1078888395 56.1711835129) (40 . 0.0000000000) (41 . 0.0000000000) (42 . 0.0000000000) (91 . 0) (10 2.5828888395 56.5594120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 3.1078888395 47.8211835129 0.0000000000) (11 -2.3921111605 46.8513851190 0.0000000000) (210 0.0000000000 0.0000000000 1.0000000000))
((0 . "LINE") (100 . "AcDbEntity") (67 . 0) (8 . "A-Window") (62 . 151) (6 . "Continuous") (100 . "AcDbLine") (10 3.1078888395 56.1711835129 0.0000000000) (11 -2.3921111605 55.2013851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 47.2396136866) (40 . 0.0000000000) (41 . 0.0000000000) (42 . 0.0000000000) (91 . 0) (10 -2.3921111605 46.8513851190) (40 . 0.0000000000) (41 . 0.0000000000) (42 . 0.0000000000) (91 . 0) (10 -1.8671111605 46.4631565513) (40 . 0.0000000000) (41 . 0.0000000000) (42 . 0.0000000000) (91 . 0) (10 2.5828888395 47.4329549452) (40 . 0.0000000000) (41 . 0.0000000000) (42 . 0.0000000000) (91 . 0) (10 3.1078888395 47.8211835129) (40 . 0.0000000000) (41 . 0.0000000000) (42 . 0.0000000000) (91 . 0) (10 2.5828888395 48.2094120805) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 57.2596136866) (40 . 0.0000000000) (41 . 0.0000000000) (42 . 0.0000000000) (91 . 0) (10 -2.3921111605 56.8713851190) (40 . 0.0000000000) (41 . 0.0000000000) (42 . 0.0000000000) (91 . 0) (10 -1.8671111605 56.4831565513) (40 . 0.0000000000) (41 . 0.0000000000) (42 . 0.0000000000) (91 . 0) (10 2.5828888395 57.4529549452) (40 . 0.0000000000) (41 . 0.0000000000) (42 . 0.0000000000) (91 . 0) (10 3.1078888395 57.8411835129) (40 . 0.0000000000) (41 . 0.0000000000) (42 . 0.0000000000) (91 . 0) (10 2.5828888395 58.2294120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 3.1078888395 57.8411835129 0.0000000000) (11 -2.3921111605 56.8713851190 0.0000000000) (210 0.0000000000 0.0000000000 1.0000000000))
((0 . "LINE") (100 . "AcDbEntity") (67 . 0) (8 . "A-Window") (62 . 151) (6 . "Continuous") (100 . "AcDbLine") (10 3.1078888395 46.1511835129 0.0000000000) (11 -2.3921111605 45.1813851190 0.0000000000) (210 0.0000000000 0.0000000000 1.0000000000))
((0 . "LWPOLYLINE") (100 . "AcDbEntity") (67 . 0) (8 . "A-Window") (62 . 151) (6 . "Continuous") (100 . "AcDbPolyline") (90 . 10) (70 . 0) (43 . 0.0000000000) (38 . 0.0000000000) (39 . 0.0000000000) (10 2.5828888395 42.6957453328) (40 . 0.0000000000) (41 . 0.0000000000) (42 . 0.0000000000) (91 . 0) (10 2.5828888395 41.0687741511) (40 . 0.0000000000) (41 . 0.0000000000) (42 . 0.0000000000) (91 . 0) (10 0.3578888395 39.2017774718) (40 . 0.0000000000) (41 . 0.0000000000) (42 . 0.0000000000) (91 . 0) (10 -1.8671111605 41.0687741511) (40 . 0.0000000000) (41 . 0.0000000000) (42 . 0.0000000000) (91 . 0) (10 -1.8671111605 43.5797314468) (40 . 0.0000000000) (41 . 0.0000000000) (42 . 0.0000000000) (91 . 0) (10 -2.1783611605 43.8709028725) (40 . 0.0000000000) (41 . 0.0000000000) (42 . 0.0000000000) (91 . 0) (10 -1.8671111605 44.1620742983) (40 . 0.0000000000) (41 . 0.0000000000) (42 . -0.2138820884) (91 . 0) (10 1.7415027540 44.6836330695) (40 . 0.0000000000) (41 . 0.0000000000) (42 . 0.0000000000) (91 . 0) (10 -0.1106380000 39.5949181700) (40 . 0.0000000000) (41 . 0.0000000000) (42 . -0.2315249815) (91 . 0) (10 2.5828888395 41.0687741511) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 2.5828888395 59.8994120805 0.0000000000) (11 2.5828888395 60.7929549452 0.0000000000) (210 0.0000000000 0.0000000000 1.0000000000))
((0 . "LINE") (100 . "AcDbEntity") (67 . 0) (8 . "A-Window") (62 . 151) (6 . "Continuous") (100 . "AcDbLine") (10 2.5828888395 61.5694120805 0.0000000000) (11 2.5828888395 62.4629549452 0.0000000000) (210 0.0000000000 0.0000000000 1.0000000000))
((0 . "LINE") (100 . "AcDbEntity") (67 . 0) (8 . "A-Window") (62 . 151) (6 . "Continuous") (100 . "AcDbLine") (10 2.5828888395 63.2394120805 0.0000000000) (11 2.5828888395 61.1329549452 0.0000000000) (210 0.0000000000 0.0000000000 1.0000000000))
((0 . "LINE") (100 . "AcDbEntity") (67 . 0) (8 . "A-Window") (62 . 151) (6 . "Continuous") (100 . "AcDbLine") (10 -1.8671111605 58.9296136866 0.0000000000) (11 -1.8671111605 59.8231565513 0.0000000000) (210 0.0000000000 0.0000000000 1.0000000000))
((0 . "LINE") (100 . "AcDbEntity") (67 . 0) (8 . "A-Window") (62 . 151) (6 . "Continuous") (100 . "AcDbLine") (10 -1.8671111605 60.5996136866 0.0000000000) (11 -1.8671111605 61.4931565513 0.0000000000) (210 0.0000000000 0.0000000000 1.0000000000))
((0 . "LINE") (100 . "AcDbEntity") (67 . 0) (8 . "A-Window") (62 . 151) (6 . "Continuous") (100 . "AcDbLine") (10 -1.8671111605 62.2696136866 0.0000000000) (11 -1.8671111605 63.1631565513 0.0000000000) (210 0.0000000000 0.0000000000 1.0000000000))
((0 . "LINE") (100 . "AcDbEntity") (67 . 0) (8 . "A-Window") (62 . 151) (6 . "Continuous") (100 . "AcDbLine") (10 3.1078888395 61.1811835129 0.0000000000) (11 -2.3921111605 60.2113851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 60.5996136866) (40 . 0.0000000000) (41 . 0.0000000000) (42 . 0.0000000000) (91 . 0) (10 -2.3921111605 60.2113851190) (40 . 0.0000000000) (41 . 0.0000000000) (42 . 0.0000000000) (91 . 0) (10 -1.8671111605 59.8231565513) (40 . 0.0000000000) (41 . 0.0000000000) (42 . 0.0000000000) (91 . 0) (10 2.5828888395 60.7929549452) (40 . 0.0000000000) (41 . 0.0000000000) (42 . 0.0000000000) (91 . 0) (10 3.1078888395 61.1811835129) (40 . 0.0000000000) (41 . 0.0000000000) (42 . 0.0000000000) (91 . 0) (10 2.5828888395 61.5694120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 3.1078888395 62.8511835129 0.0000000000) (11 -2.3921111605 61.8813851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 62.2696136866) (40 . 0.0000000000) (41 . 0.0000000000) (42 . 0.0000000000) (91 . 0) (10 -2.3921111605 61.8813851190) (40 . 0.0000000000) (41 . 0.0000000000) (42 . 0.0000000000) (91 . 0) (10 -1.8671111605 61.4931565513) (40 . 0.0000000000) (41 . 0.0000000000) (42 . 0.0000000000) (91 . 0) (10 2.5828888395 62.4629549452) (40 . 0.0000000000) (41 . 0.0000000000) (42 . 0.0000000000) (91 . 0) (10 3.1078888395 62.8511835129) (40 . 0.0000000000) (41 . 0.0000000000) (42 . 0.0000000000) (91 . 0) (10 2.5828888395 63.2394120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 3.1078888395 61.5211835128 0.0000000000) (11 -2.3921111605 63.5513851190 0.0000000000) (210 0.0000000000 0.0000000000 1.0000000000))
((0 . "LINE") (100 . "AcDbEntity") (67 . 0) (8 . "A-Window") (62 . 151) (6 . "Continuous") (100 . "AcDbLine") (10 3.1078888395 59.5111835129 0.0000000000) (11 -2.3921111605 58.5413851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 58.9296136866) (40 . 0.0000000000) (41 . 0.0000000000) (42 . 0.0000000000) (91 . 0) (10 -2.3921111605 58.5413851190) (40 . 0.0000000000) (41 . 0.0000000000) (42 . 0.0000000000) (91 . 0) (10 -1.8671111605 58.1531565513) (40 . 0.0000000000) (41 . 0.0000000000) (42 . 0.0000000000) (91 . 0) (10 2.5828888395 59.1229549452) (40 . 0.0000000000) (41 . 0.0000000000) (42 . 0.0000000000) (91 . 0) (10 3.1078888395 59.5111835129) (40 . 0.0000000000) (41 . 0.0000000000) (42 . 0.0000000000) (91 . 0) (10 2.5828888395 59.8994120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 2.5828888395 58.2294120805 0.0000000000) (11 2.5828888395 59.1229549452 0.0000000000) (210 0.0000000000 0.0000000000 1.0000000000))
((0 . "LINE") (100 . "AcDbEntity") (67 . 0) (8 . "A-Window") (62 . 151) (6 . "Continuous") (100 . "AcDbLine") (10 2.5828888395 54.8894120805 0.0000000000) (11 2.5828888395 55.7829549452 0.0000000000) (210 0.0000000000 0.0000000000 1.0000000000))
((0 . "LINE") (100 . "AcDbEntity") (67 . 0) (8 . "A-Window") (62 . 151) (6 . "Continuous") (100 . "AcDbLine") (10 -1.8671111605 53.9196136866 0.0000000000) (11 -1.8671111605 54.8131565513 0.0000000000) (210 0.0000000000 0.0000000000 1.0000000000))
((0 . "LINE") (100 . "AcDbEntity") (67 . 0) (8 . "A-Window") (62 . 151) (6 . "Continuous") (100 . "AcDbLine") (10 2.5828888395 54.8894120805 0.0000000000) (11 2.5828888395 55.7829549452 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 53.9196136866) (40 . 0.0000000000) (41 . 0.0000000000) (42 . 0.0000000000) (91 . 0) (10 -2.3921111605 53.5313851190) (40 . 0.0000000000) (41 . 0.0000000000) (42 . 0.0000000000) (91 . 0) (10 -1.8671111605 53.1431565513) (40 . 0.0000000000) (41 . 0.0000000000) (42 . 0.0000000000) (91 . 0) (10 2.5828888395 54.1129549452) (40 . 0.0000000000) (41 . 0.0000000000) (42 . 0.0000000000) (91 . 0) (10 3.1078888395 54.5011835129) (40 . 0.0000000000) (41 . 0.0000000000) (42 . 0.0000000000) (91 . 0) (10 2.5828888395 54.8894120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 3.1078888395 54.5011835129 0.0000000000) (11 -2.3921111605 53.5313851190 0.0000000000) (210 0.0000000000 0.0000000000 1.0000000000))
((0 . "LINE") (100 . "AcDbEntity") (67 . 0) (8 . "A-Window") (62 . 151) (6 . "Continuous") (100 . "AcDbLine") (10 2.5828888395 53.2194120805 0.0000000000) (11 2.5828888395 54.1129549452 0.0000000000) (210 0.0000000000 0.0000000000 1.0000000000))
((0 . "LINE") (100 . "AcDbEntity") (67 . 0) (8 . "A-Window") (62 . 151) (6 . "Continuous") (100 . "AcDbLine") (10 -1.8671111605 52.2496136866 0.0000000000) (11 -1.8671111605 53.1431565513 0.0000000000) (210 0.0000000000 0.0000000000 1.0000000000))
((0 . "LINE") (100 . "AcDbEntity") (67 . 0) (8 . "A-Window") (62 . 151) (6 . "Continuous") (100 . "AcDbLine") (10 2.5828888395 53.2194120805 0.0000000000) (11 2.5828888395 54.1129549452 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 52.2496136866) (40 . 0.0000000000) (41 . 0.0000000000) (42 . 0.0000000000) (91 . 0) (10 -2.3921111605 51.8613851189) (40 . 0.0000000000) (41 . 0.0000000000) (42 . 0.0000000000) (91 . 0) (10 -1.8671111605 51.4731565513) (40 . 0.0000000000) (41 . 0.0000000000) (42 . 0.0000000000) (91 . 0) (10 2.5828888395 52.4429549452) (40 . 0.0000000000) (41 . 0.0000000000) (42 . 0.0000000000) (91 . 0) (10 3.1078888395 52.8311835129) (40 . 0.0000000000) (41 . 0.0000000000) (42 . 0.0000000000) (91 . 0) (10 2.5828888395 53.2194120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 3.1078888395 52.8311835129 0.0000000000) (11 -2.3921111605 51.8613851189 0.0000000000) (210 0.0000000000 0.0000000000 1.0000000000))
((0 . "LINE") (100 . "AcDbEntity") (67 . 0) (8 . "A-Window") (62 . 151) (6 . "Continuous") (100 . "AcDbLine") (10 7.3578888395 71.3967000000 0.0000000000) (11 8.8578888395 71.3967000000 0.0000000000) (210 0.0000000000 0.0000000000 1.0000000000))
((0 . "LINE") (100 . "AcDbEntity") (67 . 0) (8 . "A-Window") (62 . 151) (6 . "Continuous") (100 . "AcDbLine") (10 7.3578888395 72.8917774718 0.0000000000) (11 7.3578888395 71.3967000000 0.0000000000) (210 0.0000000000 0.0000000000 1.0000000000))
((0 . "LINE") (100 . "AcDbEntity") (67 . 0) (8 . "A-Window") (62 . 151) (6 . "Continuous") (100 . "AcDbLine") (10 5.8177271261 72.8917774718 0.0000000000) (11 7.3578888395 72.8917774718 0.0000000000) (210 0.0000000000 0.0000000000 1.0000000000))
((0 . "LINE") (100 . "AcDbEntity") (67 . 0) (8 . "A-Window") (62 . 151) (6 . "Continuous") (100 . "AcDbLine") (10 -6.6421111605 71.3967000000 0.0000000000) (11 -6.6421111605 72.8917774718 0.0000000000) (210 0.0000000000 0.0000000000 1.0000000000))
((0 . "LINE") (100 . "AcDbEntity") (67 . 0) (8 . "A-Window") (62 . 151) (6 . "Continuous") (100 . "AcDbLine") (10 -8.1421111605 71.3967000000 0.0000000000) (11 -6.6421111605 71.3967000000 0.0000000000) (210 0.0000000000 0.0000000000 1.0000000000))
((0 . "LWPOLYLINE") (100 . "AcDbEntity") (67 . 0) (8 . "A-Window") (62 . 151) (6 . "Continuous") (100 . "AcDbPolyline") (90 . 4) (70 . 1) (43 . 0.0000000000) (38 . 0.0000000000) (39 . 0.0000000000) (10 7.3578888395 71.3967000000) (40 . 0.0000000000) (41 . 0.0000000000) (42 . 0.0000000000) (91 . 0) (10 -6.6421111605 71.3967000000) (40 . 0.0000000000) (41 . 0.0000000000) (42 . 0.0000000000) (91 . 0) (10 -6.6421111605 72.8917774718) (40 . 0.0000000000) (41 . 0.0000000000) (42 . 0.0000000000) (91 . 0) (10 7.3578888395 72.8917774718) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 2.5828888395 51.5494120805 0.0000000000) (11 2.5828888395 52.4429549452 0.0000000000) (210 0.0000000000 0.0000000000 1.0000000000))
((0 . "LINE") (100 . "AcDbEntity") (67 . 0) (8 . "A-Window") (62 . 151) (6 . "Continuous") (100 . "AcDbLine") (10 -1.8671111605 50.5796136866 0.0000000000) (11 -1.8671111605 51.4731565513 0.0000000000) (210 0.0000000000 0.0000000000 1.0000000000))
((0 . "LINE") (100 . "AcDbEntity") (67 . 0) (8 . "A-Window") (62 . 151) (6 . "Continuous") (100 . "AcDbLine") (10 2.5828888395 51.5494120805 0.0000000000) (11 2.5828888395 52.4429549452 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 50.5796136866) (40 . 0.0000000000) (41 . 0.0000000000) (42 . 0.0000000000) (91 . 0) (10 -2.3921111605 50.1913851190) (40 . 0.0000000000) (41 . 0.0000000000) (42 . 0.0000000000) (91 . 0) (10 -1.8671111605 49.8031565513) (40 . 0.0000000000) (41 . 0.0000000000) (42 . 0.0000000000) (91 . 0) (10 2.5828888395 50.7729549452) (40 . 0.0000000000) (41 . 0.0000000000) (42 . 0.0000000000) (91 . 0) (10 3.1078888395 51.1611835129) (40 . 0.0000000000) (41 . 0.0000000000) (42 . 0.0000000000) (91 . 0) (10 2.5828888395 51.5494120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 3.1078888395 51.1611835129 0.0000000000) (11 -2.3921111605 50.1913851190 0.0000000000) (210 0.0000000000 0.0000000000 1.0000000000))
((0 . "LINE") (100 . "AcDbEntity") (67 . 0) (8 . "A-Window") (62 . 151) (6 . "Continuous") (100 . "AcDbLine") (10 2.5828888395 49.8794120805 0.0000000000) (11 2.5828888395 50.7729549452 0.0000000000) (210 0.0000000000 0.0000000000 1.0000000000))
((0 . "LINE") (100 . "AcDbEntity") (67 . 0) (8 . "A-Window") (62 . 151) (6 . "Continuous") (100 . "AcDbLine") (10 -1.8671111605 48.9096136866 0.0000000000) (11 -1.8671111605 49.8031565513 0.0000000000) (210 0.0000000000 0.0000000000 1.0000000000))
((0 . "LINE") (100 . "AcDbEntity") (67 . 0) (8 . "A-Window") (62 . 151) (6 . "Continuous") (100 . "AcDbLine") (10 2.5828888395 49.8794120805 0.0000000000) (11 2.5828888395 50.7729549452 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 48.9096136866) (40 . 0.0000000000) (41 . 0.0000000000) (42 . 0.0000000000) (91 . 0) (10 -2.3921111605 48.5213851190) (40 . 0.0000000000) (41 . 0.0000000000) (42 . 0.0000000000) (91 . 0) (10 -1.8671111605 48.1331565513) (40 . 0.0000000000) (41 . 0.0000000000) (42 . 0.0000000000) (91 . 0) (10 2.5828888395 49.1029549452) (40 . 0.0000000000) (41 . 0.0000000000) (42 . 0.0000000000) (91 . 0) (10 3.1078888395 49.4911835129) (40 . 0.0000000000) (41 . 0.0000000000) (42 . 0.0000000000) (91 . 0) (10 2.5828888395 49.8794120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 3.1078888395 49.4911835129 0.0000000000) (11 -2.3921111605 48.5213851190 0.0000000000) (210 0.0000000000 0.0000000000 1.0000000000))
((0 . "ARC") (100 . "AcDbEntity") (67 . 0) (8 . "A-Window") (62 . 151) (6 . "Continuous") (100 . "AcDbCircle") (10 -42.8123962027 66.7859023315 0.0000000000) (40 . 10.6781898097) (210 0.0000000000 0.0000000000 1.0000000000) (100 . "AcDbArc") (50 . -0.3727943380) (51 . 0.0384802174))
((0 . "LINE") (100 . "AcDbEntity") (67 . 0) (8 . "A-Window") (62 . 151) (6 . "Continuous") (100 . "AcDbLine") (10 32.8578888394 38.1967000000 0.0000000000) (11 32.8578888394 42.8966999996 0.0000000000) (210 0.0000000000 0.0000000000 1.0000000000))
((0 . "LWPOLYLINE") (100 . "AcDbEntity") (67 . 0) (8 . "A-Window") (62 . 3) (6 . "Continuous") (100 . "AcDbPolyline") (90 . 44) (70 . 1) (43 . 0.0000000000) (38 . 0.0000000000) (39 . 0.0000000000) (10 24.3642583620 70.2966877930) (40 . 0.0000000000) (41 . 0.0000000000) (42 . 0.0000000000) (91 . 0) (10 24.3642583620 70.0967122071) (40 . 0.0000000000) (41 . 0.0000000000) (42 . 0.4142225008) (91 . 0) (10 24.7642583619 69.6967000001) (40 . 0.0000000000) (41 . 0.0000000000) (42 . 0.0000000000) (91 . 0) (10 24.9642583619 69.6967000001) (40 . 0.0000000000) (41 . 0.0000000000) (42 . -0.4142135624) (91 . 0) (10 25.5642583619 69.0967000001) (40 . 0.0000000000) (41 . 0.0000000000) (42 . 0.0000000000) (91 . 0) (10 25.5642583619 68.8967000001) (40 . 0.0000000000) (41 . 0.0000000000) (42 . -0.2513806714) (91 . 0) (10 25.2959208409 68.3967000001) (40 . 0.0000000000) (41 . 0.0000000000) (42 . 0.0000000000) (91 . 0) (10 23.5640841373 68.3967000001) (40 . 0.0000000000) (41 . 0.0000000000) (42 . 0.4142135624) (91 . 0) (10 23.0640841373 67.8967000001) (40 . 0.0000000000) (41 . 0.0000000000) (42 . 0.0000000000) (91 . 0) (10 23.0640841373 63.2967000001) (40 . 0.0000000000) (41 . 0.0000000000) (42 . 0.4142135624) (91 . 0) (10 23.5640841373 62.7967000001) (40 . 0.0000000000) (41 . 0.0000000000) (42 . 0.0000000000) (91 . 0) (10 23.7742880933 62.7967000001) (40 . 0.0000000000) (41 . 0.0000000000) (42 . 0.0000000000) (91 . 0) (10 23.9189729887 63.1989988507) (40 . 0.0000000000) (41 . 0.0000000000) (42 . 0.0000000000) (91 . 0) (10 24.2762104017 63.1989988507) (40 . 0.0000000000) (41 . 0.0000000000) (42 . 0.0000000000) (91 . 0) (10 24.4159547600 62.7967000001) (40 . 0.0000000000) (41 . 0.0000000000) (42 . 0.0000000000) (91 . 0) (10 25.0576214266 62.7967000001) (40 . 0.0000000000) (41 . 0.0000000000) (42 . 0.0000000000) (91 . 0) (10 25.2023063220 63.1989988507) (40 . 0.0000000000) (41 . 0.0000000000) (42 . 0.0000000000) (91 . 0) (10 25.5595437350 63.1989988507) (40 . 0.0000000000) (41 . 0.0000000000) (42 . 0.0000000000) (91 . 0) (10 25.6992880933 62.7967000001) (40 . 0.0000000000) (41 . 0.0000000000) (42 . 0.0000000000) (91 . 0) (10 26.3409547600 62.7967000001) (40 . 0.0000000000) (41 . 0.0000000000) (42 . 0.0000000000) (91 . 0) (10 26.4856396554 63.1989988507) (40 . 0.0000000000) (41 . 0.0000000000) (42 . 0.0000000000) (91 . 0) (10 26.8428770684 63.1989988507) (40 . 0.0000000000) (41 . 0.0000000000) (42 . 0.0000000000) (91 . 0) (10 26.9826214266 62.7967000001) (40 . 0.0000000000) (41 . 0.0000000000) (42 . 0.0000000000) (91 . 0) (10 27.6242880933 62.7967000001) (40 . 0.0000000000) (41 . 0.0000000000) (42 . 0.0000000000) (91 . 0) (10 27.7689729887 63.1989988507) (40 . 0.0000000000) (41 . 0.0000000000) (42 . 0.0000000000) (91 . 0) (10 28.1262104017 63.1989988507) (40 . 0.0000000000) (41 . 0.0000000000) (42 . 0.0000000000) (91 . 0) (10 28.2659547600 62.7967000001) (40 . 0.0000000000) (41 . 0.0000000000) (42 . 0.0000000000) (91 . 0) (10 28.9076214266 62.7967000001) (40 . 0.0000000000) (41 . 0.0000000000) (42 . 0.0000000000) (91 . 0) (10 29.0523063221 63.1989988507) (40 . 0.0000000000) (41 . 0.0000000000) (42 . 0.0000000000) (91 . 0) (10 29.4095437350 63.1989988507) (40 . 0.0000000000) (41 . 0.0000000000) (42 . 0.0000000000) (91 . 0) (10 29.5492880933 62.7967000001) (40 . 0.0000000000) (41 . 0.0000000000) (42 . 0.0000000000) (91 . 0) (10 29.7640841372 62.7967000001) (40 . 0.0000000000) (41 . 0.0000000000) (42 . 0.4142135624) (91 . 0) (10 30.2640841372 63.2967000001) (40 . 0.0000000000) (41 . 0.0000000000) (42 . 0.0000000000) (91 . 0) (10 30.2640841372 67.8967000001) (40 . 0.0000000000) (41 . 0.0000000000) (42 . 0.4142135624) (91 . 0) (10 29.7640841372 68.3967000001) (40 . 0.0000000000) (41 . 0.0000000000) (42 . 0.0000000000) (91 . 0) (10 28.0325958828 68.3967000001) (40 . 0.0000000000) (41 . 0.0000000000) (42 . -0.2513806714) (91 . 0) (10 27.7642583619 68.8967000001) (40 . 0.0000000000) (41 . 0.0000000000) (42 . 0.0000000000) (91 . 0) (10 27.7642583619 69.0967000001) (40 . 0.0000000000) (41 . 0.0000000000) (42 . -0.4142135624) (91 . 0) (10 28.3642583619 69.6967000001) (40 . 0.0000000000) (41 . 0.0000000000) (42 . 0.0000000000) (91 . 0) (10 28.5642583619 69.6967000001) (40 . 0.0000000000) (41 . 0.0000000000) (42 . 0.4142135624) (91 . 0) (10 28.9642583619 70.0967000001) (40 . 0.0000000000) (41 . 0.0000000000) (42 . 0.0000000000) (91 . 0) (10 28.9642583619 70.2967000001) (40 . 0.0000000000) (41 . 0.0000000000) (42 . 0.4142135624) (91 . 0) (10 28.5642583619 70.6967000001) (40 . 0.0000000000) (41 . 0.0000000000) (42 . 0.0000000000) (91 . 0) (10 24.7642583619 70.6967000001) (40 . 0.0000000000) (41 . 0.0000000000) (42 . 0.4142225008) (91 . 0) (210 0.0000000000 0.0000000000 1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 28.8190841372 67.3467000001) (40 . 0.0000000000) (41 . 0.0000000000) (42 . 0.0000000000) (91 . 0) (10 28.8190841372 64.2467000001) (40 . 0.0000000000) (41 . 0.0000000000) (42 . 0.0000000000) (91 . 0) (10 27.3190841372 64.2467000001) (40 . 0.0000000000) (41 . 0.0000000000) (42 . 0.0000000000) (91 . 0) (10 27.3190841372 67.3467000001) (40 . 0.0000000000) (41 . 0.0000000000) (42 . 0.0000000000) (91 . 0) (210 0.0000000000 0.0000000000 1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 25.9690841372 67.3467000001) (40 . 0.0000000000) (41 . 0.0000000000) (42 . 0.0000000000) (91 . 0) (10 25.9690841372 64.2467000001) (40 . 0.0000000000) (41 . 0.0000000000) (42 . 0.0000000000) (91 . 0) (10 24.4690841372 64.2467000001) (40 . 0.0000000000) (41 . 0.0000000000) (42 . 0.0000000000) (91 . 0) (10 24.4690841372 67.3467000001) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 32.8676567472 62.3966999996 0.0000000000) (11 32.8676567472 67.1967000011 0.0000000000) (210 0.0000000000 0.0000000000 1.0000000000))
((0 . "ARC") (100 . "AcDbEntity") (67 . 0) (8 . "A-Window") (62 . 151) (6 . "Continuous") (100 . "AcDbCircle") (10 -42.8123962027 38.2074976685 0.0000000000) (40 . 10.6781898097) (210 0.0000000000 0.0000000000 1.0000000000) (100 . "AcDbArc") (50 . -0.0384802174) (51 . 0.3727943380))
((0 . "LWPOLYLINE") (100 . "AcDbEntity") (67 . 0) (8 . "A-Window") (62 . 3) (6 . "Continuous") (100 . "AcDbPolyline") (90 . 44) (70 . 1) (43 . 0.0000000000) (38 . 0.0000000000) (39 . 0.0000000000) (10 -24.3693354697 34.6967122070) (40 . 0.0000000000) (41 . 0.0000000000) (42 . 0.0000000000) (91 . 0) (10 -24.3693354697 34.8966877930) (40 . 0.0000000000) (41 . 0.0000000000) (42 . 0.4142225008) (91 . 0) (10 -24.7693354695 35.2967000000) (40 . 0.0000000000) (41 . 0.0000000000) (42 . 0.0000000000) (91 . 0) (10 -24.9693354696 35.2967000000) (40 . 0.0000000000) (41 . 0.0000000000) (42 . -0.4142135624) (91 . 0) (10 -25.5693354696 35.8967000000) (40 . 0.0000000000) (41 . 0.0000000000) (42 . 0.0000000000) (91 . 0) (10 -25.5693354696 36.0967000000) (40 . 0.0000000000) (41 . 0.0000000000) (42 . -0.2513806714) (91 . 0) (10 -25.3009979486 36.5967000000) (40 . 0.0000000000) (41 . 0.0000000000) (42 . 0.0000000000) (91 . 0) (10 -23.5691612449 36.5967000000) (40 . 0.0000000000) (41 . 0.0000000000) (42 . 0.4142135624) (91 . 0) (10 -23.0691612449 37.0967000000) (40 . 0.0000000000) (41 . 0.0000000000) (42 . 0.0000000000) (91 . 0) (10 -23.0691612449 41.6967000000) (40 . 0.0000000000) (41 . 0.0000000000) (42 . 0.4142135624) (91 . 0) (10 -23.5691612449 42.1967000000) (40 . 0.0000000000) (41 . 0.0000000000) (42 . 0.0000000000) (91 . 0) (10 -23.7793652010 42.1967000000) (40 . 0.0000000000) (41 . 0.0000000000) (42 . 0.0000000000) (91 . 0) (10 -23.9240500964 41.7944011494) (40 . 0.0000000000) (41 . 0.0000000000) (42 . 0.0000000000) (91 . 0) (10 -24.2812875094 41.7944011494) (40 . 0.0000000000) (41 . 0.0000000000) (42 . 0.0000000000) (91 . 0) (10 -24.4210318676 42.1967000000) (40 . 0.0000000000) (41 . 0.0000000000) (42 . 0.0000000000) (91 . 0) (10 -25.0626985343 42.1967000000) (40 . 0.0000000000) (41 . 0.0000000000) (42 . 0.0000000000) (91 . 0) (10 -25.2073834297 41.7944011494) (40 . 0.0000000000) (41 . 0.0000000000) (42 . 0.0000000000) (91 . 0) (10 -25.5646208427 41.7944011494) (40 . 0.0000000000) (41 . 0.0000000000) (42 . 0.0000000000) (91 . 0) (10 -25.7043652010 42.1967000000) (40 . 0.0000000000) (41 . 0.0000000000) (42 . 0.0000000000) (91 . 0) (10 -26.3460318676 42.1967000000) (40 . 0.0000000000) (41 . 0.0000000000) (42 . 0.0000000000) (91 . 0) (10 -26.4907167631 41.7944011494) (40 . 0.0000000000) (41 . 0.0000000000) (42 . 0.0000000000) (91 . 0) (10 -26.8479541760 41.7944011494) (40 . 0.0000000000) (41 . 0.0000000000) (42 . 0.0000000000) (91 . 0) (10 -26.9876985343 42.1967000000) (40 . 0.0000000000) (41 . 0.0000000000) (42 . 0.0000000000) (91 . 0) (10 -27.6293652010 42.1967000000) (40 . 0.0000000000) (41 . 0.0000000000) (42 . 0.0000000000) (91 . 0) (10 -27.7740500964 41.7944011494) (40 . 0.0000000000) (41 . 0.0000000000) (42 . 0.0000000000) (91 . 0) (10 -28.1312875094 41.7944011494) (40 . 0.0000000000) (41 . 0.0000000000) (42 . 0.0000000000) (91 . 0) (10 -28.2710318676 42.1967000000) (40 . 0.0000000000) (41 . 0.0000000000) (42 . 0.0000000000) (91 . 0) (10 -28.9126985343 42.1967000000) (40 . 0.0000000000) (41 . 0.0000000000) (42 . 0.0000000000) (91 . 0) (10 -29.0573834297 41.7944011494) (40 . 0.0000000000) (41 . 0.0000000000) (42 . 0.0000000000) (91 . 0) (10 -29.4146208427 41.7944011494) (40 . 0.0000000000) (41 . 0.0000000000) (42 . 0.0000000000) (91 . 0) (10 -29.5543652010 42.1967000000) (40 . 0.0000000000) (41 . 0.0000000000) (42 . 0.0000000000) (91 . 0) (10 -29.7691612449 42.1967000000) (40 . 0.0000000000) (41 . 0.0000000000) (42 . 0.4142135624) (91 . 0) (10 -30.2691612449 41.6967000000) (40 . 0.0000000000) (41 . 0.0000000000) (42 . 0.0000000000) (91 . 0) (10 -30.2691612449 37.0967000000) (40 . 0.0000000000) (41 . 0.0000000000) (42 . 0.4142135624) (91 . 0) (10 -29.7691612449 36.5967000000) (40 . 0.0000000000) (41 . 0.0000000000) (42 . 0.0000000000) (91 . 0) (10 -28.0376729905 36.5967000000) (40 . 0.0000000000) (41 . 0.0000000000) (42 . -0.2513806714) (91 . 0) (10 -27.7693354695 36.0967000000) (40 . 0.0000000000) (41 . 0.0000000000) (42 . 0.0000000000) (91 . 0) (10 -27.7693354695 35.8967000000) (40 . 0.0000000000) (41 . 0.0000000000) (42 . -0.4142135624) (91 . 0) (10 -28.3693354695 35.2967000000) (40 . 0.0000000000) (41 . 0.0000000000) (42 . 0.0000000000) (91 . 0) (10 -28.5693354696 35.2967000000) (40 . 0.0000000000) (41 . 0.0000000000) (42 . 0.4142135624) (91 . 0) (10 -28.9693354696 34.8967000000) (40 . 0.0000000000) (41 . 0.0000000000) (42 . 0.0000000000) (91 . 0) (10 -28.9693354696 34.6967000000) (40 . 0.0000000000) (41 . 0.0000000000) (42 . 0.4142135624) (91 . 0) (10 -28.5693354696 34.2967000000) (40 . 0.0000000000) (41 . 0.0000000000) (42 . 0.0000000000) (91 . 0) (10 -24.7693354695 34.2967000000) (40 . 0.0000000000) (41 . 0.0000000000) (42 . 0.4142225008) (91 . 0) (210 0.0000000000 0.0000000000 1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 -28.8241612449 37.6467000000) (40 . 0.0000000000) (41 . 0.0000000000) (42 . 0.0000000000) (91 . 0) (10 -28.8241612449 40.7467000000) (40 . 0.0000000000) (41 . 0.0000000000) (42 . 0.0000000000) (91 . 0) (10 -27.3241612449 40.7467000000) (40 . 0.0000000000) (41 . 0.0000000000) (42 . 0.0000000000) (91 . 0) (10 -27.3241612449 37.6467000000) (40 . 0.0000000000) (41 . 0.0000000000) (42 . 0.0000000000) (91 . 0) (210 0.0000000000 0.0000000000 1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 -25.9741612449 37.6467000000) (40 . 0.0000000000) (41 . 0.0000000000) (42 . 0.0000000000) (91 . 0) (10 -25.9741612449 40.7467000000) (40 . 0.0000000000) (41 . 0.0000000000) (42 . 0.0000000000) (91 . 0) (10 -24.4741612449 40.7467000000) (40 . 0.0000000000) (41 . 0.0000000000) (42 . 0.0000000000) (91 . 0) (10 -24.4741612449 37.6467000000) (40 . 0.0000000000) (41 . 0.0000000000) (42 . 0.0000000000) (91 . 0) (210 0.0000000000 0.0000000000 1.0000000000))
((0 . "LWPOLYLINE") (100 . "AcDbEntity") (67 . 0) (8 . "A-Window") (62 . 3) (6 . "Continuous") (100 . "AcDbPolyline") (90 . 44) (70 . 1) (43 . 0.0000000000) (38 . 0.0000000000) (39 . 0.0000000000) (10 -25.0851131488 34.6967122070) (40 . 0.0000000000) (41 . 0.0000000000) (42 . 0.0000000000) (91 . 0) (10 -25.0851131488 34.8966877930) (40 . 0.0000000000) (41 . 0.0000000000) (42 . 0.4142225008) (91 . 0) (10 -25.4851131486 35.2967000000) (40 . 0.0000000000) (41 . 0.0000000000) (42 . 0.0000000000) (91 . 0) (10 -25.6851131486 35.2967000000) (40 . 0.0000000000) (41 . 0.0000000000) (42 . -0.4142135624) (91 . 0) (10 -26.2851131486 35.8967000000) (40 . 0.0000000000) (41 . 0.0000000000) (42 . 0.0000000000) (91 . 0) (10 -26.2851131486 36.0967000000) (40 . 0.0000000000) (41 . 0.0000000000) (42 . -0.2513806714) (91 . 0) (10 -26.0167756276 36.5967000000) (40 . 0.0000000000) (41 . 0.0000000000) (42 . 0.0000000000) (91 . 0) (10 -24.2849389240 36.5967000000) (40 . 0.0000000000) (41 . 0.0000000000) (42 . 0.4142135624) (91 . 0) (10 -23.7849389240 37.0967000000) (40 . 0.0000000000) (41 . 0.0000000000) (42 . 0.0000000000) (91 . 0) (10 -23.7849389240 41.6967000000) (40 . 0.0000000000) (41 . 0.0000000000) (42 . 0.4142135624) (91 . 0) (10 -24.2849389240 42.1967000000) (40 . 0.0000000000) (41 . 0.0000000000) (42 . 0.0000000000) (91 . 0) (10 -24.4951428800 42.1967000000) (40 . 0.0000000000) (41 . 0.0000000000) (42 . 0.0000000000) (91 . 0) (10 -24.6398277754 41.7944011494) (40 . 0.0000000000) (41 . 0.0000000000) (42 . 0.0000000000) (91 . 0) (10 -24.9970651884 41.7944011494) (40 . 0.0000000000) (41 . 0.0000000000) (42 . 0.0000000000) (91 . 0) (10 -25.1368095467 42.1967000000) (40 . 0.0000000000) (41 . 0.0000000000) (42 . 0.0000000000) (91 . 0) (10 -25.7784762133 42.1967000000) (40 . 0.0000000000) (41 . 0.0000000000) (42 . 0.0000000000) (91 . 0) (10 -25.9231611088 41.7944011494) (40 . 0.0000000000) (41 . 0.0000000000) (42 . 0.0000000000) (91 . 0) (10 -26.2803985217 41.7944011494) (40 . 0.0000000000) (41 . 0.0000000000) (42 . 0.0000000000) (91 . 0) (10 -26.4201428800 42.1967000000) (40 . 0.0000000000) (41 . 0.0000000000) (42 . 0.0000000000) (91 . 0) (10 -27.0618095467 42.1967000000) (40 . 0.0000000000) (41 . 0.0000000000) (42 . 0.0000000000) (91 . 0) (10 -27.2064944421 41.7944011494) (40 . 0.0000000000) (41 . 0.0000000000) (42 . 0.0000000000) (91 . 0) (10 -27.5637318551 41.7944011494) (40 . 0.0000000000) (41 . 0.0000000000) (42 . 0.0000000000) (91 . 0) (10 -27.7034762133 42.1967000000) (40 . 0.0000000000) (41 . 0.0000000000) (42 . 0.0000000000) (91 . 0) (10 -28.3451428800 42.1967000000) (40 . 0.0000000000) (41 . 0.0000000000) (42 . 0.0000000000) (91 . 0) (10 -28.4898277754 41.7944011494) (40 . 0.0000000000) (41 . 0.0000000000) (42 . 0.0000000000) (91 . 0) (10 -28.8470651884 41.7944011494) (40 . 0.0000000000) (41 . 0.0000000000) (42 . 0.0000000000) (91 . 0) (10 -28.9868095467 42.1967000000) (40 . 0.0000000000) (41 . 0.0000000000) (42 . 0.0000000000) (91 . 0) (10 -29.6284762133 42.1967000000) (40 . 0.0000000000) (41 . 0.0000000000) (42 . 0.0000000000) (91 . 0) (10 -29.7731611088 41.7944011494) (40 . 0.0000000000) (41 . 0.0000000000) (42 . 0.0000000000) (91 . 0) (10 -30.1303985217 41.7944011494) (40 . 0.0000000000) (41 . 0.0000000000) (42 . 0.0000000000) (91 . 0) (10 -30.2701428800 42.1967000000) (40 . 0.0000000000) (41 . 0.0000000000) (42 . 0.0000000000) (91 . 0) (10 -30.4849389239 42.1967000000) (40 . 0.0000000000) (41 . 0.0000000000) (42 . 0.4142135624) (91 . 0) (10 -30.9849389239 41.6967000000) (40 . 0.0000000000) (41 . 0.0000000000) (42 . 0.0000000000) (91 . 0) (10 -30.9849389239 37.0967000000) (40 . 0.0000000000) (41 . 0.0000000000) (42 . 0.4142135624) (91 . 0) (10 -30.4849389239 36.5967000000) (40 . 0.0000000000) (41 . 0.0000000000) (42 . 0.0000000000) (91 . 0) (10 -28.7534506695 36.5967000000) (40 . 0.0000000000) (41 . 0.0000000000) (42 . -0.2513806714) (91 . 0) (10 -28.4851131486 36.0967000000) (40 . 0.0000000000) (41 . 0.0000000000) (42 . 0.0000000000) (91 . 0) (10 -28.4851131486 35.8967000000) (40 . 0.0000000000) (41 . 0.0000000000) (42 . -0.4142135624) (91 . 0) (10 -29.0851131486 35.2967000000) (40 . 0.0000000000) (41 . 0.0000000000) (42 . 0.0000000000) (91 . 0) (10 -29.2851131486 35.2967000000) (40 . 0.0000000000) (41 . 0.0000000000) (42 . 0.4142135624) (91 . 0) (10 -29.6851131486 34.8967000000) (40 . 0.0000000000) (41 . 0.0000000000) (42 . 0.0000000000) (91 . 0) (10 -29.6851131486 34.6967000000) (40 . 0.0000000000) (41 . 0.0000000000) (42 . 0.4142135624) (91 . 0) (10 -29.2851131486 34.2967000000) (40 . 0.0000000000) (41 . 0.0000000000) (42 . 0.0000000000) (91 . 0) (10 -25.4851131486 34.2967000000) (40 . 0.0000000000) (41 . 0.0000000000) (42 . 0.4142225008) (91 . 0) (210 0.0000000000 0.0000000000 -1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 -29.5399389240 37.6467000000) (40 . 0.0000000000) (41 . 0.0000000000) (42 . 0.0000000000) (91 . 0) (10 -29.5399389240 40.7467000000) (40 . 0.0000000000) (41 . 0.0000000000) (42 . 0.0000000000) (91 . 0) (10 -28.0399389240 40.7467000000) (40 . 0.0000000000) (41 . 0.0000000000) (42 . 0.0000000000) (91 . 0) (10 -28.0399389240 37.6467000000) (40 . 0.0000000000) (41 . 0.0000000000) (42 . 0.0000000000) (91 . 0) (210 0.0000000000 0.0000000000 -1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 -26.6899389239 37.6467000000) (40 . 0.0000000000) (41 . 0.0000000000) (42 . 0.0000000000) (91 . 0) (10 -26.6899389239 40.7467000000) (40 . 0.0000000000) (41 . 0.0000000000) (42 . 0.0000000000) (91 . 0) (10 -25.1899389239 40.7467000000) (40 . 0.0000000000) (41 . 0.0000000000) (42 . 0.0000000000) (91 . 0) (10 -25.1899389239 37.6467000000) (40 . 0.0000000000) (41 . 0.0000000000) (42 . 0.0000000000) (91 . 0) (210 0.0000000000 0.0000000000 -1.0000000000))
)
("VK_CuaSoMo"
((0 . "LWPOLYLINE") (100 . "AcDbEntity") (67 . 0) (8 . "A-Window") (62 . 151) (6 . "Continuous") (100 . "AcDbPolyline") (90 . 8) (70 . 1) (43 . 0.0000000000) (38 . 0.0000000000) (39 . 0.0000000000) (10 970.1421111598 -90.5967000000) (40 . 0.0000000000) (41 . 0.0000000000) (42 . -0.4142135624) (91 . 0) (10 969.6421111598 -90.0967000000) (40 . 0.0000000000) (41 . 0.0000000000) (42 . 0.0000000000) (91 . 0) (10 969.6421111598 30.4967000000) (40 . 0.0000000000) (41 . 0.0000000000) (42 . -0.4142135624) (91 . 0) (10 970.1421111598 30.9967000000) (40 . 0.0000000000) (41 . 0.0000000000) (42 . 0.0000000000) (91 . 0) (10 1029.1421111598 30.9967000000) (40 . 0.0000000000) (41 . 0.0000000000) (42 . -0.4142135624) (91 . 0) (10 1029.6421111598 30.4967000000) (40 . 0.0000000000) (41 . 0.0000000000) (42 . 0.0000000000) (91 . 0) (10 1029.6421111598 -90.0967000000) (40 . 0.0000000000) (41 . 0.0000000000) (42 . -0.4142135624) (91 . 0) (10 1029.1421111598 -90.5967000000) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 87) (70 . 1) (43 . 0.0000000000) (38 . 0.0000000000) (39 . 0.0000000000) (10 970.2421111598 34.6967000000) (40 . 0.0000000000) (41 . 0.0000000000) (42 . 0.0000000000) (91 . 0) (10 970.2421111598 34.4967000000) (40 . 0.0000000000) (41 . 0.0000000000) (42 . 0.4142135624) (91 . 0) (10 970.7421111598 33.9967000000) (40 . 0.0000000000) (41 . 0.0000000000) (42 . 0.0000000000) (91 . 0) (10 974.5421111598 33.9967000000) (40 . 0.0000000000) (41 . 0.0000000000) (42 . 0.4142135624) (91 . 0) (10 975.0421111598 34.4967000000) (40 . 0.0000000000) (41 . 0.0000000000) (42 . 0.0000000000) (91 . 0) (10 975.0421111598 34.6967000000) (40 . 0.0000000000) (41 . 0.0000000000) (42 . 0.4142135624) (91 . 0) (10 974.5421111598 35.1967000000) (40 . 0.0000000000) (41 . 0.0000000000) (42 . 0.0000000000) (91 . 0) (10 974.3421111598 35.1967000000) (40 . 0.0000000000) (41 . 0.0000000000) (42 . -0.4142135624) (91 . 0) (10 973.8421111598 35.6967000000) (40 . 0.0000000000) (41 . 0.0000000000) (42 . 0.0000000000) (91 . 0) (10 973.8421111598 35.8967000000) (40 . 0.0000000000) (41 . 0.0000000000) (42 . -0.4142135624) (91 . 0) (10 974.3421111598 36.3967000000) (40 . 0.0000000000) (41 . 0.0000000000) (42 . 0.0000000000) (91 . 0) (10 975.7421111598 36.3967000000) (40 . 0.0000000000) (41 . 0.0000000000) (42 . -0.4142135624) (91 . 0) (10 976.2421111598 35.8967000000) (40 . 0.0000000000) (41 . 0.0000000000) (42 . 0.0000000000) (91 . 0) (10 976.2421111598 34.4967000000) (40 . 0.0000000000) (41 . 0.0000000000) (42 . 0.4142135624) (91 . 0) (10 976.7421111598 33.9967000000) (40 . 0.0000000000) (41 . 0.0000000000) (42 . 0.0000000000) (91 . 0) (10 990.6421111598 33.9967000000) (40 . 0.0000000000) (41 . 0.0000000000) (42 . 0.4142135624) (91 . 0) (10 991.1421111598 34.4967000000) (40 . 0.0000000000) (41 . 0.0000000000) (42 . 0.0000000000) (91 . 0) (10 991.1421111598 55.8967000000) (40 . 0.0000000000) (41 . 0.0000000000) (42 . -0.4142135624) (91 . 0) (10 991.6421111598 56.3967000000) (40 . 0.0000000000) (41 . 0.0000000000) (42 . 0.0000000000) (91 . 0) (10 993.9421063550 56.3967000000) (40 . 0.0000000000) (41 . 0.0000000000) (42 . 0.0000000000) (91 . 0) (10 994.9190568379 54.4427990332) (40 . 0.0000000000) (41 . 0.0000000000) (42 . -0.4142135643) (91 . 0) (10 994.8296141176 54.1744708754) (40 . 0.0000000000) (41 . 0.0000000000) (42 . 0.0000000000) (91 . 0) (10 994.6507286814 54.0850281587) (40 . 0.0000000000) (41 . 0.0000000000) (42 . 0.4142135643) (91 . 0) (10 994.5612859611 53.8167000008) (40 . 0.0000000000) (41 . 0.0000000000) (42 . 0.0000000000) (91 . 0) (10 995.1660073213 52.6072572806) (40 . 0.0000000000) (41 . 0.0000000000) (42 . 0.2840790438) (91 . 0) (10 995.3448927595 52.4966999997) (40 . 0.0000000000) (41 . 0.0000000000) (42 . 0.0000000000) (91 . 0) (10 998.9764257348 52.4966999997) (40 . 0.0000000000) (41 . 0.0000000000) (42 . -0.1989123674) (91 . 0) (10 999.1178470910 52.4381213559) (40 . 0.0000000000) (41 . 0.0000000000) (42 . 0.0000000000) (91 . 0) (10 999.5006898035 52.0552786434) (40 . 0.0000000000) (41 . 0.0000000000) (42 . 0.1989123674) (91 . 0) (10 999.6421111597 51.9966999997) (40 . 0.0000000000) (41 . 0.0000000000) (42 . 0.1989123674) (91 . 0) (10 999.7835325160 52.0552786434) (40 . 0.0000000000) (41 . 0.0000000000) (42 . 0.0000000000) (91 . 0) (10 1000.1663752284 52.4381213559) (40 . 0.0000000000) (41 . 0.0000000000) (42 . -0.1989123674) (91 . 0) (10 1000.3077965847 52.4966999997) (40 . 0.0000000000) (41 . 0.0000000000) (42 . 0.0000000000) (91 . 0) (10 1003.9393295599 52.4966999997) (40 . 0.0000000000) (41 . 0.0000000000) (42 . 0.2840790438) (91 . 0) (10 1004.1182149980 52.6072572805) (40 . 0.0000000000) (41 . 0.0000000000) (42 . 0.0000000000) (91 . 0) (10 1004.7229363585 53.8167000007) (40 . 0.0000000000) (41 . 0.0000000000) (42 . 0.4142135642) (91 . 0) (10 1004.6334936383 54.0850281586) (40 . 0.0000000000) (41 . 0.0000000000) (42 . 0.0000000000) (91 . 0) (10 1004.4546082018 54.1744708755) (40 . 0.0000000000) (41 . 0.0000000000) (42 . -0.4142135641) (91 . 0) (10 1004.3651654816 54.4427990333) (40 . 0.0000000000) (41 . 0.0000000000) (42 . 0.0000000000) (91 . 0) (10 1005.3421159645 56.3967000000) (40 . 0.0000000000) (41 . 0.0000000000) (42 . 0.0000000000) (91 . 0) (10 1007.6421111598 56.3967000000) (40 . 0.0000000000) (41 . 0.0000000000) (42 . -0.4142135624) (91 . 0) (10 1008.1421111598 55.8967000000) (40 . 0.0000000000) (41 . 0.0000000000) (42 . 0.0000000000) (91 . 0) (10 1008.1421111598 34.4967000000) (40 . 0.0000000000) (41 . 0.0000000000) (42 . 0.4142135624) (91 . 0) (10 1008.6421111598 33.9967000000) (40 . 0.0000000000) (41 . 0.0000000000) (42 . 0.0000000000) (91 . 0) (10 1022.5421111598 33.9967000000) (40 . 0.0000000000) (41 . 0.0000000000) (42 . 0.4142135624) (91 . 0) (10 1023.0421111598 34.4967000000) (40 . 0.0000000000) (41 . 0.0000000000) (42 . 0.0000000000) (91 . 0) (10 1023.0421111598 35.8967000000) (40 . 0.0000000000) (41 . 0.0000000000) (42 . -0.4142135624) (91 . 0) (10 1023.5421111598 36.3967000000) (40 . 0.0000000000) (41 . 0.0000000000) (42 . 0.0000000000) (91 . 0) (10 1024.9421111598 36.3967000000) (40 . 0.0000000000) (41 . 0.0000000000) (42 . -0.4142135624) (91 . 0) (10 1025.4421111598 35.8967000000) (40 . 0.0000000000) (41 . 0.0000000000) (42 . 0.0000000000) (91 . 0) (10 1025.4421111598 35.6967000000) (40 . 0.0000000000) (41 . 0.0000000000) (42 . -0.4142135624) (91 . 0) (10 1024.9421111598 35.1967000000) (40 . 0.0000000000) (41 . 0.0000000000) (42 . 0.0000000000) (91 . 0) (10 1024.7421111598 35.1967000000) (40 . 0.0000000000) (41 . 0.0000000000) (42 . 0.4142135624) (91 . 0) (10 1024.2421111598 34.6967000000) (40 . 0.0000000000) (41 . 0.0000000000) (42 . 0.0000000000) (91 . 0) (10 1024.2421111598 34.4967000000) (40 . 0.0000000000) (41 . 0.0000000000) (42 . 0.4142135624) (91 . 0) (10 1024.7421111598 33.9967000000) (40 . 0.0000000000) (41 . 0.0000000000) (42 . 0.0000000000) (91 . 0) (10 1028.5421111598 33.9967000000) (40 . 0.0000000000) (41 . 0.0000000000) (42 . 0.4142135624) (91 . 0) (10 1029.0421111598 34.4967000000) (40 . 0.0000000000) (41 . 0.0000000000) (42 . 0.0000000000) (91 . 0) (10 1029.0421111598 34.6967000000) (40 . 0.0000000000) (41 . 0.0000000000) (42 . 0.4142135624) (91 . 0) (10 1028.5421111598 35.1967000000) (40 . 0.0000000000) (41 . 0.0000000000) (42 . 0.0000000000) (91 . 0) (10 1028.3421111598 35.1967000000) (40 . 0.0000000000) (41 . 0.0000000000) (42 . -0.4142135624) (91 . 0) (10 1027.8421111598 35.6967000000) (40 . 0.0000000000) (41 . 0.0000000000) (42 . 0.0000000000) (91 . 0) (10 1027.8421111598 35.8967000000) (40 . 0.0000000000) (41 . 0.0000000000) (42 . -0.4142135624) (91 . 0) (10 1028.3421111598 36.3967000000) (40 . 0.0000000000) (41 . 0.0000000000) (42 . 0.0000000000) (91 . 0) (10 1030.4421111598 36.3967000000) (40 . 0.0000000000) (41 . 0.0000000000) (42 . 0.4142135624) (91 . 0) (10 1030.9421111598 36.8967000000) (40 . 0.0000000000) (41 . 0.0000000000) (42 . 0.0000000000) (91 . 0) (10 1030.9421111598 37.8967000000) (40 . 0.0000000000) (41 . 0.0000000000) (42 . -0.4142135624) (91 . 0) (10 1031.4421111598 38.3967000000) (40 . 0.0000000000) (41 . 0.0000000000) (42 . 0.0000000000) (91 . 0) (10 1031.6421111598 38.3967000000) (40 . 0.0000000000) (41 . 0.0000000000) (42 . -0.4142135624) (91 . 0) (10 1032.1421111598 37.8967000000) (40 . 0.0000000000) (41 . 0.0000000000) (42 . 0.0000000000) (91 . 0) (10 1032.1421111598 33.9967000000) (40 . 0.0000000000) (41 . 0.0000000000) (42 . 0.0000000000) (91 . 0) (10 1032.1421111598 -93.0967000000) (40 . 0.0000000000) (41 . 0.0000000000) (42 . -0.4142135624) (91 . 0) (10 1031.6421111598 -93.5967000000) (40 . 0.0000000000) (41 . 0.0000000000) (42 . 0.0000000000) (91 . 0) (10 967.6421111598 -93.5967000000) (40 . 0.0000000000) (41 . 0.0000000000) (42 . -0.4142135624) (91 . 0) (10 967.1421111598 -93.0967000000) (40 . 0.0000000000) (41 . 0.0000000000) (42 . 0.0000000000) (91 . 0) (10 967.1421111598 33.9967000000) (40 . 0.0000000000) (41 . 0.0000000000) (42 . 0.0000000000) (91 . 0) (10 967.1421111598 37.8967000000) (40 . 0.0000000000) (41 . 0.0000000000) (42 . -0.4142135624) (91 . 0) (10 967.6421111598 38.3967000000) (40 . 0.0000000000) (41 . 0.0000000000) (42 . 0.0000000000) (91 . 0) (10 967.8421111598 38.3967000000) (40 . 0.0000000000) (41 . 0.0000000000) (42 . -0.4142135624) (91 . 0) (10 968.3421111598 37.8967000000) (40 . 0.0000000000) (41 . 0.0000000000) (42 . 0.0000000000) (91 . 0) (10 968.3421111598 36.8967000000) (40 . 0.0000000000) (41 . 0.0000000000) (42 . 0.4142135624) (91 . 0) (10 968.8421111598 36.3967000000) (40 . 0.0000000000) (41 . 0.0000000000) (42 . 0.0000000000) (91 . 0) (10 970.9421111598 36.3967000000) (40 . 0.0000000000) (41 . 0.0000000000) (42 . -0.4142135624) (91 . 0) (10 971.4421111598 35.8967000000) (40 . 0.0000000000) (41 . 0.0000000000) (42 . 0.0000000000) (91 . 0) (10 971.4421111598 35.6967000000) (40 . 0.0000000000) (41 . 0.0000000000) (42 . -0.4142135624) (91 . 0) (10 970.9421111598 35.1967000000) (40 . 0.0000000000) (41 . 0.0000000000) (42 . 0.0000000000) (91 . 0) (10 970.7421111598 35.1967000000) (40 . 0.0000000000) (41 . 0.0000000000) (42 . 0.4142135624) (91 . 0) (210 0.0000000000 0.0000000000 1.0000000000))
((0 . "LWPOLYLINE") (100 . "AcDbEntity") (67 . 0) (8 . "A-Window") (62 . 151) (6 . "Continuous") (100 . "AcDbPolyline") (90 . 17) (70 . 1) (43 . 0.0000000000) (38 . 0.0000000000) (39 . 0.0000000000) (10 999.6421111597 47.4966999996) (40 . 0.0000000000) (41 . 0.0000000000) (42 . 0.0000000000) (91 . 0) (10 1002.8235760292 47.4966999996) (40 . 0.0000000000) (41 . 0.0000000000) (42 . 0.2914734196) (91 . 0) (10 1003.2767299227 47.7853908688) (40 . 0.0000000000) (41 . 0.0000000000) (42 . 0.0000000000) (91 . 0) (10 1004.1732615419 49.7080091306) (40 . 0.0000000000) (41 . 0.0000000000) (42 . -0.2914734196) (91 . 0) (10 1004.6264154354 49.9966999997) (40 . 0.0000000000) (41 . 0.0000000000) (42 . 0.0000000000) (91 . 0) (10 1005.6421111597 49.9966999997) (40 . 0.0000000000) (41 . 0.0000000000) (42 . -0.4142135624) (91 . 0) (10 1006.1421111597 49.4966999997) (40 . 0.0000000000) (41 . 0.0000000000) (42 . 0.0000000000) (91 . 0) (10 1006.1421111597 34.4967000000) (40 . 0.0000000000) (41 . 0.0000000000) (42 . -0.4142135624) (91 . 0) (10 1005.6421111597 33.9967000000) (40 . 0.0000000000) (41 . 0.0000000000) (42 . 0.0000000000) (91 . 0) (10 993.6421111597 33.9967000000) (40 . 0.0000000000) (41 . 0.0000000000) (42 . -0.4142135624) (91 . 0) (10 993.1421111597 34.4967000000) (40 . 0.0000000000) (41 . 0.0000000000) (42 . 0.0000000000) (91 . 0) (10 993.1421111597 49.4966999997) (40 . 0.0000000000) (41 . 0.0000000000) (42 . -0.4142135624) (91 . 0) (10 993.6421111597 49.9966999997) (40 . 0.0000000000) (41 . 0.0000000000) (42 . 0.0000000000) (91 . 0) (10 994.6578068838 49.9966999997) (40 . 0.0000000000) (41 . 0.0000000000) (42 . -0.2914734196) (91 . 0) (10 995.1109607773 49.7080091306) (40 . 0.0000000000) (41 . 0.0000000000) (42 . 0.0000000000) (91 . 0) (10 996.0074923965 47.7853908688) (40 . 0.0000000000) (41 . 0.0000000000) (42 . 0.2914734196) (91 . 0) (10 996.4606462900 47.4966999996) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 12) (70 . 1) (43 . 0.0000000000) (38 . 0.0000000000) (39 . 0.0000000000) (10 993.8532489466 61.6983038651) (40 . 0.0000000000) (41 . 0.0000000000) (42 . -0.2849552787) (91 . 0) (10 993.7421111673 61.8774783771) (40 . 0.0000000000) (41 . 0.0000000000) (42 . 0.0000000000) (91 . 0) (10 993.7421111673 61.7734539607) (40 . 0.0000000000) (41 . 0.0000000000) (42 . -0.5564744028) (91 . 0) (10 994.4642667191 62.2213902406) (40 . 0.0000000000) (41 . 0.0000000000) (42 . 0.0000000000) (91 . 0) (10 999.4199556074 62.7635991465) (40 . 0.0000000000) (41 . 0.0000000000) (42 . 0.2343570514) (91 . 0) (10 999.8642667105 62.7635991463) (40 . 0.0000000000) (41 . 0.0000000000) (42 . 0.0000000000) (91 . 0) (10 1004.8199556158 62.2213902421) (40 . 0.0000000000) (41 . 0.0000000000) (42 . -0.5564744024) (91 . 0) (10 1005.5421111671 61.7734539620) (40 . 0.0000000000) (41 . 0.0000000000) (42 . 0.0000000000) (91 . 0) (10 1005.5421111671 61.8774783772) (40 . 0.0000000000) (41 . 0.0000000000) (42 . -0.2849552790) (91 . 0) (10 1005.4309733876 61.6983038651) (40 . 0.0000000000) (41 . 0.0000000000) (42 . 0.0000000000) (91 . 0) (10 999.8642667110 58.9374763869) (40 . 0.0000000000) (41 . 0.0000000000) (42 . -0.2343570514) (91 . 0) (10 999.4199556080 58.9374763871) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 65) (70 . 0) (43 . 0.0000000000) (38 . 0.0000000000) (39 . 0.0000000000) (10 995.1421111672 67.1313221971) (40 . 0.0000000000) (41 . 0.0000000000) (42 . 0.0000000000) (91 . 0) (10 995.1421111672 66.5967000000) (40 . 0.0000000000) (41 . 0.0000000000) (42 . -0.4142135624) (91 . 0) (10 994.9421111670 66.3967000000) (40 . 0.0000000000) (41 . 0.0000000000) (42 . 0.0000000000) (91 . 0) (10 993.9421111670 66.3967000000) (40 . 0.0000000000) (41 . 0.0000000000) (42 . 0.4142135624) (91 . 0) (10 993.7421111673 66.1967000000) (40 . 0.0000000000) (41 . 0.0000000000) (42 . 0.0000000000) (91 . 0) (10 993.7421111673 64.3779464253) (40 . 0.0000000000) (41 . 0.0000000000) (42 . 0.2849552787) (91 . 0) (10 993.8532489466 64.1987719134) (40 . 0.0000000000) (41 . 0.0000000000) (42 . 0.0000000000) (91 . 0) (10 999.4199556083 61.4379444351) (40 . 0.0000000000) (41 . 0.0000000000) (42 . 0.2343570514) (91 . 0) (10 999.8642667114 61.4379444349) (40 . 0.0000000000) (41 . 0.0000000000) (42 . 0.0000000000) (91 . 0) (10 1005.4309733876 64.1987719129) (40 . 0.0000000000) (41 . 0.0000000000) (42 . 0.2849552790) (91 . 0) (10 1005.5421111671 64.3779464250) (40 . 0.0000000000) (41 . 0.0000000000) (42 . 0.0000000000) (91 . 0) (10 1005.5421111671 66.1967000000) (40 . 0.0000000000) (41 . 0.0000000000) (42 . 0.4142135624) (91 . 0) (10 1005.3421111669 66.3966999999) (40 . 0.0000000000) (41 . 0.0000000000) (42 . 0.0000000000) (91 . 0) (10 1004.3421111669 66.3966999999) (40 . 0.0000000000) (41 . 0.0000000000) (42 . -0.4142135624) (91 . 0) (10 1004.1421111672 66.5967000000) (40 . 0.0000000000) (41 . 0.0000000000) (42 . 0.0000000000) (91 . 0) (10 1004.1421111672 67.1189032619) (40 . 0.0000000000) (41 . 0.0000000000) (42 . -0.1876437528) (91 . 0) (10 1004.1946803391 67.2540481876) (40 . 0.0000000000) (41 . 0.0000000000) (42 . 0.0000000000) (91 . 0) (10 1005.1826606825 68.3318449257) (40 . 0.0000000000) (41 . 0.0000000000) (42 . -0.2102297862) (91 . 0) (10 1005.3300915103 68.3966999999) (40 . 0.0000000000) (41 . 0.0000000000) (42 . 0.0000000000) (91 . 0) (10 1006.9421111670 68.3966999999) (40 . 0.0000000000) (41 . 0.0000000000) (42 . -0.4142135624) (91 . 0) (10 1007.1421111672 68.1967000000) (40 . 0.0000000000) (41 . 0.0000000000) (42 . 0.0000000000) (91 . 0) (10 1007.1421111672 56.5967000000) (40 . 0.0000000000) (41 . 0.0000000000) (42 . -0.4142135624) (91 . 0) (10 1006.9421111670 56.3966999999) (40 . 0.0000000000) (41 . 0.0000000000) (42 . 0.0000000000) (91 . 0) (10 1005.9421111670 56.3966999999) (40 . 0.0000000000) (41 . 0.0000000000) (42 . -0.4142135624) (91 . 0) (10 1005.7421111673 56.5967000000) (40 . 0.0000000000) (41 . 0.0000000000) (42 . 0.0000000000) (91 . 0) (10 1005.7421111673 59.0967000000) (40 . 0.0000000000) (41 . 0.0000000000) (42 . 0.5788431251) (91 . 0) (10 1004.9901756545 59.5285894504) (40 . 0.0000000000) (41 . 0.0000000000) (42 . 0.0000000000) (91 . 0) (10 1004.4199556153 59.2457868447) (40 . 0.0000000000) (41 . 0.0000000000) (42 . 0.2849552788) (91 . 0) (10 1004.1421111672 58.7978505647) (40 . 0.0000000000) (41 . 0.0000000000) (42 . 0.0000000000) (91 . 0) (10 1004.1421111672 54.3533563146) (40 . 0.0000000000) (41 . 0.0000000000) (42 . 0.2840790438) (91 . 0) (10 1004.2526684481 54.1744708764) (40 . 0.0000000000) (41 . 0.0000000000) (42 . 0.0000000000) (91 . 0) (10 1004.4315538862 54.0850281572) (40 . 0.0000000000) (41 . 0.0000000000) (42 . -0.4142135624) (91 . 0) (10 1004.5209966054 53.8167000000) (40 . 0.0000000000) (41 . 0.0000000000) (42 . 0.0000000000) (91 . 0) (10 1003.9162752454 52.6072572809) (40 . 0.0000000000) (41 . 0.0000000000) (42 . -0.2840790438) (91 . 0) (10 1003.7373898074 52.4967000000) (40 . 0.0000000000) (41 . 0.0000000000) (42 . 0.0000000000) (91 . 0) (10 1003.0609966054 52.4967000000) (40 . 0.0000000000) (41 . 0.0000000000) (42 . -0.4142135624) (91 . 0) (10 1002.8609966052 52.6967000000) (40 . 0.0000000000) (41 . 0.0000000000) (42 . 0.0000000000) (91 . 0) (10 1002.8609966053 57.9432778508) (40 . 0.0000000000) (41 . 0.0000000000) (42 . 0.5564744024) (91 . 0) (10 1002.1388410540 58.3912141310) (40 . 0.0000000000) (41 . 0.0000000000) (42 . 0.0000000000) (91 . 0) (10 999.7309733791 57.1970238086) (40 . 0.0000000000) (41 . 0.0000000000) (42 . -0.2343570514) (91 . 0) (10 999.5532489378 57.1970238087) (40 . 0.0000000000) (41 . 0.0000000000) (42 . 0.0000000000) (91 . 0) (10 997.1453812809 58.3912141254) (40 . 0.0000000000) (41 . 0.0000000000) (42 . 0.5564744028) (91 . 0) (10 996.4232257291 57.9432778455) (40 . 0.0000000000) (41 . 0.0000000000) (42 . 0.0000000000) (91 . 0) (10 996.4232257291 52.6967000000) (40 . 0.0000000000) (41 . 0.0000000000) (42 . -0.4142135624) (91 . 0) (10 996.2232257289 52.4967000000) (40 . 0.0000000000) (41 . 0.0000000000) (42 . 0.0000000000) (91 . 0) (10 995.5468325264 52.4967000000) (40 . 0.0000000000) (41 . 0.0000000000) (42 . -0.2840790438) (91 . 0) (10 995.3679470884 52.6072572809) (40 . 0.0000000000) (41 . 0.0000000000) (42 . 0.0000000000) (91 . 0) (10 994.7632257290 53.8167000000) (40 . 0.0000000000) (41 . 0.0000000000) (42 . -0.4142135624) (91 . 0) (10 994.8526684478 54.0850281573) (40 . 0.0000000000) (41 . 0.0000000000) (42 . 0.0000000000) (91 . 0) (10 995.0315538863 54.1744708764) (40 . 0.0000000000) (41 . 0.0000000000) (42 . 0.2840790438) (91 . 0) (10 995.1421111672 54.3533563146) (40 . 0.0000000000) (41 . 0.0000000000) (42 . 0.0000000000) (91 . 0) (10 995.1421111672 58.7978505647) (40 . 0.0000000000) (41 . 0.0000000000) (42 . 0.2849552788) (91 . 0) (10 994.8642667186 59.2457868447) (40 . 0.0000000000) (41 . 0.0000000000) (42 . 0.0000000000) (91 . 0) (10 994.2940466799 59.5285894504) (40 . 0.0000000000) (41 . 0.0000000000) (42 . 0.5788431251) (91 . 0) (10 993.5421111671 59.0967000000) (40 . 0.0000000000) (41 . 0.0000000000) (42 . 0.0000000000) (91 . 0) (10 993.5421111671 56.5967000000) (40 . 0.0000000000) (41 . 0.0000000000) (42 . -0.4142135624) (91 . 0) (10 993.3421111669 56.3967000000) (40 . 0.0000000000) (41 . 0.0000000000) (42 . 0.0000000000) (91 . 0) (10 992.3421111669 56.3967000000) (40 . 0.0000000000) (41 . 0.0000000000) (42 . -0.4142135624) (91 . 0) (10 992.1421111672 56.5967000000) (40 . 0.0000000000) (41 . 0.0000000000) (42 . 0.0000000000) (91 . 0) (10 992.1421111672 68.1967000000) (40 . 0.0000000000) (41 . 0.0000000000) (42 . -0.4142135624) (91 . 0) (10 992.3421111669 68.3967000000) (40 . 0.0000000000) (41 . 0.0000000000) (42 . 0.0000000000) (91 . 0) (10 993.9545167713 68.3966999999) (40 . 0.0000000000) (41 . 0.0000000000) (42 . -0.2102297862) (91 . 0) (10 994.1019475992 68.3318449257) (40 . 0.0000000000) (41 . 0.0000000000) (42 . 0.0000000000) (91 . 0) (10 995.0899279426 67.2540481876) (40 . 0.0000000000) (41 . 0.0000000000) (42 . -0.1876437528) (91 . 0) (10 995.1424971145 67.1189032619) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 80) (70 . 1) (43 . 0.0000000000) (38 . 0.0000000000) (39 . 0.0000000000) (10 1020.9421111594 72.8967000000) (40 . 0.0000000000) (41 . 0.0000000000) (42 . -0.4142135624) (91 . 0) (10 1021.4421111594 73.3967000000) (40 . 0.0000000000) (41 . 0.0000000000) (42 . 0.0000000000) (91 . 0) (10 1028.0421111594 73.3967000000) (40 . 0.0000000000) (41 . 0.0000000000) (42 . 0.4142135624) (91 . 0) (10 1028.5421111594 73.8967000000) (40 . 0.0000000000) (41 . 0.0000000000) (42 . 0.0000000000) (91 . 0) (10 1028.5421111594 77.8967000000) (40 . 0.0000000000) (41 . 0.0000000000) (42 . -0.4142135624) (91 . 0) (10 1029.0421111594 78.3967000000) (40 . 0.0000000000) (41 . 0.0000000000) (42 . 0.0000000000) (91 . 0) (10 1029.3405054528 78.3967000000) (40 . 0.0000000000) (41 . 0.0000000000) (42 . -0.3152987889) (91 . 0) (10 1029.8103517632 78.0677100716) (40 . 0.0000000000) (41 . 0.0000000000) (42 . 0.0000000000) (91 . 0) (10 1030.4300496836 76.3651040286) (40 . 0.0000000000) (41 . 0.0000000000) (42 . -0.5205670506) (91 . 0) (10 1030.2421111594 76.0967000000) (40 . 0.0000000000) (41 . 0.0000000000) (42 . 0.0000000000) (91 . 0) (10 1030.0421111594 76.0967000000) (40 . 0.0000000000) (41 . 0.0000000000) (42 . 0.4142135624) (91 . 0) (10 1029.7421111594 75.7967000000) (40 . 0.0000000000) (41 . 0.0000000000) (42 . 0.0000000000) (91 . 0) (10 1029.7421111594 73.8967000000) (40 . 0.0000000000) (41 . 0.0000000000) (42 . 0.4142135624) (91 . 0) (10 1030.2421111594 73.3967000000) (40 . 0.0000000000) (41 . 0.0000000000) (42 . 0.0000000000) (91 . 0) (10 1030.4421111594 73.3967000000) (40 . 0.0000000000) (41 . 0.0000000000) (42 . -0.4142135624) (91 . 0) (10 1030.9421111594 72.8967000000) (40 . 0.0000000000) (41 . 0.0000000000) (42 . 0.0000000000) (91 . 0) (10 1030.9421111594 68.8967000000) (40 . 0.0000000000) (41 . 0.0000000000) (42 . -0.4142135624) (91 . 0) (10 1030.4421111594 68.3967000000) (40 . 0.0000000000) (41 . 0.0000000000) (42 . 0.0000000000) (91 . 0) (10 1027.6421111594 68.3967000000) (40 . 0.0000000000) (41 . 0.0000000000) (42 . -0.4142135624) (91 . 0) (10 1027.1421111594 68.8967000000) (40 . 0.0000000000) (41 . 0.0000000000) (42 . 0.0000000000) (91 . 0) (10 1027.1421111594 69.0967000000) (40 . 0.0000000000) (41 . 0.0000000000) (42 . -0.4142135624) (91 . 0) (10 1027.6421111594 69.5967000000) (40 . 0.0000000000) (41 . 0.0000000000) (42 . 0.0000000000) (91 . 0) (10 1028.0421111594 69.5967000000) (40 . 0.0000000000) (41 . 0.0000000000) (42 . 0.4142135624) (91 . 0) (10 1028.5421111594 70.0967000000) (40 . 0.0000000000) (41 . 0.0000000000) (42 . 0.0000000000) (91 . 0) (10 1028.5421111594 70.7967000000) (40 . 0.0000000000) (41 . 0.0000000000) (42 . 0.4142135624) (91 . 0) (10 1028.0421111594 71.2967000000) (40 . 0.0000000000) (41 . 0.0000000000) (42 . 0.0000000000) (91 . 0) (10 1023.8421111594 71.2967000000) (40 . 0.0000000000) (41 . 0.0000000000) (42 . 0.4142135624) (91 . 0) (10 1023.3421111594 70.7967000000) (40 . 0.0000000000) (41 . 0.0000000000) (42 . 0.0000000000) (91 . 0) (10 1023.3421111594 70.0967000000) (40 . 0.0000000000) (41 . 0.0000000000) (42 . 0.4142135624) (91 . 0) (10 1023.8421111594 69.5967000000) (40 . 0.0000000000) (41 . 0.0000000000) (42 . 0.0000000000) (91 . 0) (10 1024.2421111594 69.5967000000) (40 . 0.0000000000) (41 . 0.0000000000) (42 . -0.4142135624) (91 . 0) (10 1024.7421111594 69.0967000000) (40 . 0.0000000000) (41 . 0.0000000000) (42 . 0.0000000000) (91 . 0) (10 1024.7421111594 68.8967000000) (40 . 0.0000000000) (41 . 0.0000000000) (42 . -0.4142135624) (91 . 0) (10 1024.2421111594 68.3967000000) (40 . 0.0000000000) (41 . 0.0000000000) (42 . 0.0000000000) (91 . 0) (10 999.6421111594 68.3967000000) (40 . 0.0000000000) (41 . 0.0000000000) (42 . 0.0000000000) (91 . 0) (10 975.0421111594 68.3967000000) (40 . 0.0000000000) (41 . 0.0000000000) (42 . -0.4142135624) (91 . 0) (10 974.5421111594 68.8967000000) (40 . 0.0000000000) (41 . 0.0000000000) (42 . 0.0000000000) (91 . 0) (10 974.5421111594 69.0967000000) (40 . 0.0000000000) (41 . 0.0000000000) (42 . -0.4142135624) (91 . 0) (10 975.0421111594 69.5967000000) (40 . 0.0000000000) (41 . 0.0000000000) (42 . 0.0000000000) (91 . 0) (10 975.4421111594 69.5967000000) (40 . 0.0000000000) (41 . 0.0000000000) (42 . 0.4142135624) (91 . 0) (10 975.9421111594 70.0967000000) (40 . 0.0000000000) (41 . 0.0000000000) (42 . 0.0000000000) (91 . 0) (10 975.9421111594 70.7967000000) (40 . 0.0000000000) (41 . 0.0000000000) (42 . 0.4142135624) (91 . 0) (10 975.4421111594 71.2967000000) (40 . 0.0000000000) (41 . 0.0000000000) (42 . 0.0000000000) (91 . 0) (10 971.2421111594 71.2967000000) (40 . 0.0000000000) (41 . 0.0000000000) (42 . 0.4142135624) (91 . 0) (10 970.7421111594 70.7967000000) (40 . 0.0000000000) (41 . 0.0000000000) (42 . 0.0000000000) (91 . 0) (10 970.7421111594 70.0967000000) (40 . 0.0000000000) (41 . 0.0000000000) (42 . 0.4142135624) (91 . 0) (10 971.2421111594 69.5967000000) (40 . 0.0000000000) (41 . 0.0000000000) (42 . 0.0000000000) (91 . 0) (10 971.6421111594 69.5967000000) (40 . 0.0000000000) (41 . 0.0000000000) (42 . -0.4142135624) (91 . 0) (10 972.1421111594 69.0967000000) (40 . 0.0000000000) (41 . 0.0000000000) (42 . 0.0000000000) (91 . 0) (10 972.1421111594 68.8967000000) (40 . 0.0000000000) (41 . 0.0000000000) (42 . -0.4142135624) (91 . 0) (10 971.6421111594 68.3967000000) (40 . 0.0000000000) (41 . 0.0000000000) (42 . 0.0000000000) (91 . 0) (10 968.8421111594 68.3967000000) (40 . 0.0000000000) (41 . 0.0000000000) (42 . -0.4142135624) (91 . 0) (10 968.3421111594 68.8967000000) (40 . 0.0000000000) (41 . 0.0000000000) (42 . 0.0000000000) (91 . 0) (10 968.3421111594 72.8967000000) (40 . 0.0000000000) (41 . 0.0000000000) (42 . -0.4142135624) (91 . 0) (10 968.8421111594 73.3967000000) (40 . 0.0000000000) (41 . 0.0000000000) (42 . 0.0000000000) (91 . 0) (10 969.0421111594 73.3967000000) (40 . 0.0000000000) (41 . 0.0000000000) (42 . 0.4142135624) (91 . 0) (10 969.5421111594 73.8967000000) (40 . 0.0000000000) (41 . 0.0000000000) (42 . 0.0000000000) (91 . 0) (10 969.5421111594 75.7967000000) (40 . 0.0000000000) (41 . 0.0000000000) (42 . 0.4142135624) (91 . 0) (10 969.2421111594 76.0967000000) (40 . 0.0000000000) (41 . 0.0000000000) (42 . 0.0000000000) (91 . 0) (10 969.0421111594 76.0967000000) (40 . 0.0000000000) (41 . 0.0000000000) (42 . -0.5205670506) (91 . 0) (10 968.8541726353 76.3651040286) (40 . 0.0000000000) (41 . 0.0000000000) (42 . 0.0000000000) (91 . 0) (10 969.4738705556 78.0677100716) (40 . 0.0000000000) (41 . 0.0000000000) (42 . -0.3152987889) (91 . 0) (10 969.9437168660 78.3967000000) (40 . 0.0000000000) (41 . 0.0000000000) (42 . 0.0000000000) (91 . 0) (10 970.2421111594 78.3967000000) (40 . 0.0000000000) (41 . 0.0000000000) (42 . -0.4142135624) (91 . 0) (10 970.7421111594 77.8967000000) (40 . 0.0000000000) (41 . 0.0000000000) (42 . 0.0000000000) (91 . 0) (10 970.7421111594 73.8967000000) (40 . 0.0000000000) (41 . 0.0000000000) (42 . 0.4142135624) (91 . 0) (10 971.2421111594 73.3967000000) (40 . 0.0000000000) (41 . 0.0000000000) (42 . 0.0000000000) (91 . 0) (10 977.8421111594 73.3967000000) (40 . 0.0000000000) (41 . 0.0000000000) (42 . -0.4142135624) (91 . 0) (10 978.3421111594 72.8967000000) (40 . 0.0000000000) (41 . 0.0000000000) (42 . 0.0000000000) (91 . 0) (10 978.3421111594 71.8967000000) (40 . 0.0000000000) (41 . 0.0000000000) (42 . 0.4142135624) (91 . 0) (10 978.8421111594 71.3967000000) (40 . 0.0000000000) (41 . 0.0000000000) (42 . 0.0000000000) (91 . 0) (10 998.9764257345 71.3967000000) (40 . 0.0000000000) (41 . 0.0000000000) (42 . -0.1989123674) (91 . 0) (10 999.1178470907 71.3381213562) (40 . 0.0000000000) (41 . 0.0000000000) (42 . 0.0000000000) (91 . 0) (10 999.5006898032 70.9552786438) (40 . 0.0000000000) (41 . 0.0000000000) (42 . 0.1989123674) (91 . 0) (10 999.6421111594 70.8967000000) (40 . 0.0000000000) (41 . 0.0000000000) (42 . 0.1989123674) (91 . 0) (10 999.7835325157 70.9552786438) (40 . 0.0000000000) (41 . 0.0000000000) (42 . 0.0000000000) (91 . 0) (10 1000.1663752281 71.3381213562) (40 . 0.0000000000) (41 . 0.0000000000) (42 . -0.1989123674) (91 . 0) (10 1000.3077965844 71.3967000000) (40 . 0.0000000000) (41 . 0.0000000000) (42 . 0.0000000000) (91 . 0) (10 1020.4421111594 71.3967000000) (40 . 0.0000000000) (41 . 0.0000000000) (42 . 0.4142135624) (91 . 0) (10 1020.9421111594 71.8967000000) (40 . 0.0000000000) (41 . 0.0000000000) (42 . 0.0000000000) (91 . 0) (210 0.0000000000 0.0000000000 1.0000000000))
((0 . "LWPOLYLINE") (100 . "AcDbEntity") (67 . 0) (8 . "A-Window") (62 . 3) (6 . "Continuous") (100 . "AcDbPolyline") (90 . 44) (70 . 1) (43 . 0.0000000000) (38 . 0.0000000000) (39 . 0.0000000000) (10 1023.6421111602 70.2966877930) (40 . 0.0000000000) (41 . 0.0000000000) (42 . 0.0000000000) (91 . 0) (10 1023.6421111602 70.0967122070) (40 . 0.0000000000) (41 . 0.0000000000) (42 . 0.4142225008) (91 . 0) (10 1024.0421111600 69.6967000000) (40 . 0.0000000000) (41 . 0.0000000000) (42 . 0.0000000000) (91 . 0) (10 1024.2421111600 69.6967000000) (40 . 0.0000000000) (41 . 0.0000000000) (42 . -0.4142135624) (91 . 0) (10 1024.8421111600 69.0967000000) (40 . 0.0000000000) (41 . 0.0000000000) (42 . 0.0000000000) (91 . 0) (10 1024.8421111600 68.8967000000) (40 . 0.0000000000) (41 . 0.0000000000) (42 . -0.2513806714) (91 . 0) (10 1024.5737736390 68.3967000000) (40 . 0.0000000000) (41 . 0.0000000000) (42 . 0.0000000000) (91 . 0) (10 1022.8419369354 68.3967000000) (40 . 0.0000000000) (41 . 0.0000000000) (42 . 0.4142135624) (91 . 0) (10 1022.3419369354 67.8967000000) (40 . 0.0000000000) (41 . 0.0000000000) (42 . 0.0000000000) (91 . 0) (10 1022.3419369354 63.2967000000) (40 . 0.0000000000) (41 . 0.0000000000) (42 . 0.4142135624) (91 . 0) (10 1022.8419369354 62.7967000000) (40 . 0.0000000000) (41 . 0.0000000000) (42 . 0.0000000000) (91 . 0) (10 1023.0521408914 62.7967000000) (40 . 0.0000000000) (41 . 0.0000000000) (42 . 0.0000000000) (91 . 0) (10 1023.1968257868 63.1989988506) (40 . 0.0000000000) (41 . 0.0000000000) (42 . 0.0000000000) (91 . 0) (10 1023.5540631998 63.1989988506) (40 . 0.0000000000) (41 . 0.0000000000) (42 . 0.0000000000) (91 . 0) (10 1023.6938075581 62.7967000000) (40 . 0.0000000000) (41 . 0.0000000000) (42 . 0.0000000000) (91 . 0) (10 1024.3354742248 62.7967000000) (40 . 0.0000000000) (41 . 0.0000000000) (42 . 0.0000000000) (91 . 0) (10 1024.4801591202 63.1989988506) (40 . 0.0000000000) (41 . 0.0000000000) (42 . 0.0000000000) (91 . 0) (10 1024.8373965332 63.1989988506) (40 . 0.0000000000) (41 . 0.0000000000) (42 . 0.0000000000) (91 . 0) (10 1024.9771408914 62.7967000000) (40 . 0.0000000000) (41 . 0.0000000000) (42 . 0.0000000000) (91 . 0) (10 1025.6188075581 62.7967000000) (40 . 0.0000000000) (41 . 0.0000000000) (42 . 0.0000000000) (91 . 0) (10 1025.7634924535 63.1989988506) (40 . 0.0000000000) (41 . 0.0000000000) (42 . 0.0000000000) (91 . 0) (10 1026.1207298665 63.1989988506) (40 . 0.0000000000) (41 . 0.0000000000) (42 . 0.0000000000) (91 . 0) (10 1026.2604742248 62.7967000000) (40 . 0.0000000000) (41 . 0.0000000000) (42 . 0.0000000000) (91 . 0) (10 1026.9021408914 62.7967000000) (40 . 0.0000000000) (41 . 0.0000000000) (42 . 0.0000000000) (91 . 0) (10 1027.0468257868 63.1989988506) (40 . 0.0000000000) (41 . 0.0000000000) (42 . 0.0000000000) (91 . 0) (10 1027.4040631998 63.1989988506) (40 . 0.0000000000) (41 . 0.0000000000) (42 . 0.0000000000) (91 . 0) (10 1027.5438075581 62.7967000000) (40 . 0.0000000000) (41 . 0.0000000000) (42 . 0.0000000000) (91 . 0) (10 1028.1854742248 62.7967000000) (40 . 0.0000000000) (41 . 0.0000000000) (42 . 0.0000000000) (91 . 0) (10 1028.3301591202 63.1989988506) (40 . 0.0000000000) (41 . 0.0000000000) (42 . 0.0000000000) (91 . 0) (10 1028.6873965332 63.1989988506) (40 . 0.0000000000) (41 . 0.0000000000) (42 . 0.0000000000) (91 . 0) (10 1028.8271408914 62.7967000000) (40 . 0.0000000000) (41 . 0.0000000000) (42 . 0.0000000000) (91 . 0) (10 1029.0419369354 62.7967000000) (40 . 0.0000000000) (41 . 0.0000000000) (42 . 0.4142135624) (91 . 0) (10 1029.5419369354 63.2967000000) (40 . 0.0000000000) (41 . 0.0000000000) (42 . 0.0000000000) (91 . 0) (10 1029.5419369354 67.8967000000) (40 . 0.0000000000) (41 . 0.0000000000) (42 . 0.4142135624) (91 . 0) (10 1029.0419369354 68.3967000000) (40 . 0.0000000000) (41 . 0.0000000000) (42 . 0.0000000000) (91 . 0) (10 1027.3104486810 68.3967000000) (40 . 0.0000000000) (41 . 0.0000000000) (42 . -0.2513806714) (91 . 0) (10 1027.0421111600 68.8967000000) (40 . 0.0000000000) (41 . 0.0000000000) (42 . 0.0000000000) (91 . 0) (10 1027.0421111600 69.0967000000) (40 . 0.0000000000) (41 . 0.0000000000) (42 . -0.4142135624) (91 . 0) (10 1027.6421111600 69.6967000000) (40 . 0.0000000000) (41 . 0.0000000000) (42 . 0.0000000000) (91 . 0) (10 1027.8421111600 69.6967000000) (40 . 0.0000000000) (41 . 0.0000000000) (42 . 0.4142135624) (91 . 0) (10 1028.2421111600 70.0967000000) (40 . 0.0000000000) (41 . 0.0000000000) (42 . 0.0000000000) (91 . 0) (10 1028.2421111600 70.2967000000) (40 . 0.0000000000) (41 . 0.0000000000) (42 . 0.4142135624) (91 . 0) (10 1027.8421111600 70.6967000000) (40 . 0.0000000000) (41 . 0.0000000000) (42 . 0.0000000000) (91 . 0) (10 1024.0421111600 70.6967000000) (40 . 0.0000000000) (41 . 0.0000000000) (42 . 0.4142225008) (91 . 0) (210 0.0000000000 0.0000000000 1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 1028.0969369354 67.3467000000) (40 . 0.0000000000) (41 . 0.0000000000) (42 . 0.0000000000) (91 . 0) (10 1028.0969369354 64.2467000000) (40 . 0.0000000000) (41 . 0.0000000000) (42 . 0.0000000000) (91 . 0) (10 1026.5969369354 64.2467000000) (40 . 0.0000000000) (41 . 0.0000000000) (42 . 0.0000000000) (91 . 0) (10 1026.5969369354 67.3467000000) (40 . 0.0000000000) (41 . 0.0000000000) (42 . 0.0000000000) (91 . 0) (210 0.0000000000 0.0000000000 1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 1025.2469369354 67.3467000000) (40 . 0.0000000000) (41 . 0.0000000000) (42 . 0.0000000000) (91 . 0) (10 1025.2469369354 64.2467000000) (40 . 0.0000000000) (41 . 0.0000000000) (42 . 0.0000000000) (91 . 0) (10 1023.7469369354 64.2467000000) (40 . 0.0000000000) (41 . 0.0000000000) (42 . 0.0000000000) (91 . 0) (10 1023.7469369354 67.3467000000) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 44) (70 . 1) (43 . 0.0000000000) (38 . 0.0000000000) (39 . 0.0000000000) (10 968.3421111594 91.8967000000) (40 . 0.0000000000) (41 . 0.0000000000) (42 . 0.0000000000) (91 . 0) (10 968.3421111594 80.7967000000) (40 . 0.0000000000) (41 . 0.0000000000) (42 . 0.4142135624) (91 . 0) (10 968.8421111594 80.2967000000) (40 . 0.0000000000) (41 . 0.0000000000) (42 . 0.0000000000) (91 . 0) (10 970.8421111594 80.2967000000) (40 . 0.0000000000) (41 . 0.0000000000) (42 . -0.4142135624) (91 . 0) (10 971.3421111594 79.7967000000) (40 . 0.0000000000) (41 . 0.0000000000) (42 . 0.0000000000) (91 . 0) (10 971.3421111594 79.5967000000) (40 . 0.0000000000) (41 . 0.0000000000) (42 . -0.4142135624) (91 . 0) (10 970.8421111594 79.0967000000) (40 . 0.0000000000) (41 . 0.0000000000) (42 . 0.0000000000) (91 . 0) (10 968.8421111594 79.0967000000) (40 . 0.0000000000) (41 . 0.0000000000) (42 . 0.4142135624) (91 . 0) (10 968.3421111594 78.5967000000) (40 . 0.0000000000) (41 . 0.0000000000) (42 . 0.0000000000) (91 . 0) (10 968.3421111594 76.2967000000) (40 . 0.0000000000) (41 . 0.0000000000) (42 . 0.4142135624) (91 . 0) (10 968.5421111594 76.0967000000) (40 . 0.0000000000) (41 . 0.0000000000) (42 . 0.0000000000) (91 . 0) (10 969.2242643654 76.0967000000) (40 . 0.0000000000) (41 . 0.0000000000) (42 . -0.5522631265) (91 . 0) (10 969.4045689769 75.8101537865) (40 . 0.0000000000) (41 . 0.0000000000) (42 . 0.0000000000) (91 . 0) (10 968.3618065479 73.6377320594) (40 . 0.0000000000) (41 . 0.0000000000) (42 . 0.1123491485) (91 . 0) (10 968.3421111594 73.5511858458) (40 . 0.0000000000) (41 . 0.0000000000) (42 . 0.0000000000) (91 . 0) (10 968.3421111594 67.1967000000) (40 . 0.0000000000) (41 . 0.0000000000) (42 . -0.4142135624) (91 . 0) (10 967.7421111594 66.5967000000) (40 . 0.0000000000) (41 . 0.0000000000) (42 . -0.4142135624) (91 . 0) (10 967.1421111594 67.1967000000) (40 . 0.0000000000) (41 . 0.0000000000) (42 . 0.0000000000) (91 . 0) (10 967.1421111594 93.0967000000) (40 . 0.0000000000) (41 . 0.0000000000) (42 . -0.4142135624) (91 . 0) (10 967.6421111594 93.5967000000) (40 . 0.0000000000) (41 . 0.0000000000) (42 . 0.0000000000) (91 . 0) (10 999.6421111594 93.5967000000) (40 . 0.0000000000) (41 . 0.0000000000) (42 . 0.0000000000) (91 . 0) (10 1031.6421111594 93.5967000000) (40 . 0.0000000000) (41 . 0.0000000000) (42 . -0.4142135624) (91 . 0) (10 1032.1421111594 93.0967000000) (40 . 0.0000000000) (41 . 0.0000000000) (42 . 0.0000000000) (91 . 0) (10 1032.1421111594 67.1967000000) (40 . 0.0000000000) (41 . 0.0000000000) (42 . -0.4142135624) (91 . 0) (10 1031.5421111594 66.5967000000) (40 . 0.0000000000) (41 . 0.0000000000) (42 . -0.4142135624) (91 . 0) (10 1030.9421111594 67.1967000000) (40 . 0.0000000000) (41 . 0.0000000000) (42 . 0.0000000000) (91 . 0) (10 1030.9421111594 73.5511858458) (40 . 0.0000000000) (41 . 0.0000000000) (42 . 0.1123491485) (91 . 0) (10 1030.9224157709 73.6377320594) (40 . 0.0000000000) (41 . 0.0000000000) (42 . 0.0000000000) (91 . 0) (10 1029.8796533419 75.8101537865) (40 . 0.0000000000) (41 . 0.0000000000) (42 . -0.5522631265) (91 . 0) (10 1030.0599579534 76.0967000000) (40 . 0.0000000000) (41 . 0.0000000000) (42 . 0.0000000000) (91 . 0) (10 1030.7421111594 76.0967000000) (40 . 0.0000000000) (41 . 0.0000000000) (42 . 0.4142135624) (91 . 0) (10 1030.9421111594 76.2967000000) (40 . 0.0000000000) (41 . 0.0000000000) (42 . 0.0000000000) (91 . 0) (10 1030.9421111594 78.5967000000) (40 . 0.0000000000) (41 . 0.0000000000) (42 . 0.4142135624) (91 . 0) (10 1030.4421111594 79.0967000000) (40 . 0.0000000000) (41 . 0.0000000000) (42 . 0.0000000000) (91 . 0) (10 1028.4421111594 79.0967000000) (40 . 0.0000000000) (41 . 0.0000000000) (42 . -0.4142135624) (91 . 0) (10 1027.9421111594 79.5967000000) (40 . 0.0000000000) (41 . 0.0000000000) (42 . 0.0000000000) (91 . 0) (10 1027.9421111594 79.7967000000) (40 . 0.0000000000) (41 . 0.0000000000) (42 . -0.4142135624) (91 . 0) (10 1028.4421111594 80.2967000000) (40 . 0.0000000000) (41 . 0.0000000000) (42 . 0.0000000000) (91 . 0) (10 1030.4421111594 80.2967000000) (40 . 0.0000000000) (41 . 0.0000000000) (42 . 0.4142135624) (91 . 0) (10 1030.9421111594 80.7967000000) (40 . 0.0000000000) (41 . 0.0000000000) (42 . 0.0000000000) (91 . 0) (10 1030.9421111594 91.8967000000) (40 . 0.0000000000) (41 . 0.0000000000) (42 . 0.4142135624) (91 . 0) (10 1030.4421111594 92.3967000000) (40 . 0.0000000000) (41 . 0.0000000000) (42 . 0.0000000000) (91 . 0) (10 999.6421111594 92.3967000000) (40 . 0.0000000000) (41 . 0.0000000000) (42 . 0.0000000000) (91 . 0) (10 968.8421111594 92.3967000000) (40 . 0.0000000000) (41 . 0.0000000000) (42 . 0.4142135624) (91 . 0) (210 0.0000000000 0.0000000000 1.0000000000))
((0 . "LINE") (100 . "AcDbEntity") (67 . 0) (8 . "A-Window") (62 . 151) (6 . "Continuous") (100 . "AcDbLine") (10 997.4171111597 59.8994120805 0.0000000000) (11 997.4171111597 60.7929549452 0.0000000000) (210 0.0000000000 0.0000000000 1.0000000000))
((0 . "LINE") (100 . "AcDbEntity") (67 . 0) (8 . "A-Window") (62 . 151) (6 . "Continuous") (100 . "AcDbLine") (10 997.4171111597 61.5694120805 0.0000000000) (11 997.4171111597 62.4629549452 0.0000000000) (210 0.0000000000 0.0000000000 1.0000000000))
((0 . "LINE") (100 . "AcDbEntity") (67 . 0) (8 . "A-Window") (62 . 151) (6 . "Continuous") (100 . "AcDbLine") (10 997.4171111597 56.5594120805 0.0000000000) (11 997.4171111597 57.4529549452 0.0000000000) (210 0.0000000000 0.0000000000 1.0000000000))
((0 . "LINE") (100 . "AcDbEntity") (67 . 0) (8 . "A-Window") (62 . 151) (6 . "Continuous") (100 . "AcDbLine") (10 997.4171111597 58.2294120805 0.0000000000) (11 997.4171111597 59.1229549452 0.0000000000) (210 0.0000000000 0.0000000000 1.0000000000))
((0 . "LINE") (100 . "AcDbEntity") (67 . 0) (8 . "A-Window") (62 . 151) (6 . "Continuous") (100 . "AcDbLine") (10 1001.8671111597 55.5896136866 0.0000000000) (11 1001.8671111597 56.4831565513 0.0000000000) (210 0.0000000000 0.0000000000 1.0000000000))
((0 . "LINE") (100 . "AcDbEntity") (67 . 0) (8 . "A-Window") (62 . 151) (6 . "Continuous") (100 . "AcDbLine") (10 1001.8671111597 57.2596136866 0.0000000000) (11 1001.8671111597 58.1531565513 0.0000000000) (210 0.0000000000 0.0000000000 1.0000000000))
((0 . "LINE") (100 . "AcDbEntity") (67 . 0) (8 . "A-Window") (62 . 151) (6 . "Continuous") (100 . "AcDbLine") (10 1001.8671111597 58.9296136866 0.0000000000) (11 1001.8671111597 59.8231565513 0.0000000000) (210 0.0000000000 0.0000000000 1.0000000000))
((0 . "LINE") (100 . "AcDbEntity") (67 . 0) (8 . "A-Window") (62 . 151) (6 . "Continuous") (100 . "AcDbLine") (10 1001.8671111597 60.5996136866 0.0000000000) (11 1001.8671111597 61.4931565513 0.0000000000) (210 0.0000000000 0.0000000000 1.0000000000))
((0 . "LINE") (100 . "AcDbEntity") (67 . 0) (8 . "A-Window") (62 . 151) (6 . "Continuous") (100 . "AcDbLine") (10 1001.8671111597 62.2696136866 0.0000000000) (11 1001.8671111597 63.1631565513 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1001.8671111597 57.2596136866) (40 . 0.0000000000) (41 . 0.0000000000) (42 . 0.0000000000) (91 . 0) (10 1002.3921111597 56.8713851190) (40 . 0.0000000000) (41 . 0.0000000000) (42 . 0.0000000000) (91 . 0) (10 1001.8671111597 56.4831565513) (40 . 0.0000000000) (41 . 0.0000000000) (42 . 0.0000000000) (91 . 0) (10 997.4171111597 57.4529549452) (40 . 0.0000000000) (41 . 0.0000000000) (42 . 0.0000000000) (91 . 0) (10 996.8921111597 57.8411835128) (40 . 0.0000000000) (41 . 0.0000000000) (42 . 0.0000000000) (91 . 0) (10 997.4171111597 58.2294120805) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1001.8671111597 60.5996136866) (40 . 0.0000000000) (41 . 0.0000000000) (42 . 0.0000000000) (91 . 0) (10 1002.3921111597 60.2113851190) (40 . 0.0000000000) (41 . 0.0000000000) (42 . 0.0000000000) (91 . 0) (10 1001.8671111597 59.8231565513) (40 . 0.0000000000) (41 . 0.0000000000) (42 . 0.0000000000) (91 . 0) (10 997.4171111597 60.7929549452) (40 . 0.0000000000) (41 . 0.0000000000) (42 . 0.0000000000) (91 . 0) (10 996.8921111597 61.1811835129) (40 . 0.0000000000) (41 . 0.0000000000) (42 . 0.0000000000) (91 . 0) (10 997.4171111597 61.5694120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 996.8921111597 59.5111835129 0.0000000000) (11 1002.3921111597 58.5413851190 0.0000000000) (210 0.0000000000 0.0000000000 1.0000000000))
((0 . "LINE") (100 . "AcDbEntity") (67 . 0) (8 . "A-Window") (62 . 151) (6 . "Continuous") (100 . "AcDbLine") (10 996.8921111597 61.1811835129 0.0000000000) (11 1002.3921111597 60.2113851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1001.8671111597 58.9296136866) (40 . 0.0000000000) (41 . 0.0000000000) (42 . 0.0000000000) (91 . 0) (10 1002.3921111597 58.5413851190) (40 . 0.0000000000) (41 . 0.0000000000) (42 . 0.0000000000) (91 . 0) (10 1001.8671111597 58.1531565513) (40 . 0.0000000000) (41 . 0.0000000000) (42 . 0.0000000000) (91 . 0) (10 997.4171111597 59.1229549452) (40 . 0.0000000000) (41 . 0.0000000000) (42 . 0.0000000000) (91 . 0) (10 996.8921111597 59.5111835129) (40 . 0.0000000000) (41 . 0.0000000000) (42 . 0.0000000000) (91 . 0) (10 997.4171111597 59.8994120805) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1001.8671111597 62.2696136866) (40 . 0.0000000000) (41 . 0.0000000000) (42 . 0.0000000000) (91 . 0) (10 1002.3921111597 61.8813851190) (40 . 0.0000000000) (41 . 0.0000000000) (42 . 0.0000000000) (91 . 0) (10 1001.8671111597 61.4931565513) (40 . 0.0000000000) (41 . 0.0000000000) (42 . 0.0000000000) (91 . 0) (10 997.4171111597 62.4629549452) (40 . 0.0000000000) (41 . 0.0000000000) (42 . 0.0000000000) (91 . 0) (10 996.8921111597 62.8511835129) (40 . 0.0000000000) (41 . 0.0000000000) (42 . 0.0000000000) (91 . 0) (10 997.4171111597 63.2394120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 996.8921111597 62.8511835129 0.0000000000) (11 1002.3921111597 61.8813851190 0.0000000000) (210 0.0000000000 0.0000000000 1.0000000000))
((0 . "LINE") (100 . "AcDbEntity") (67 . 0) (8 . "A-Window") (62 . 151) (6 . "Continuous") (100 . "AcDbLine") (10 996.8921111597 57.8411835128 0.0000000000) (11 1002.3921111597 56.8713851190 0.0000000000) (210 0.0000000000 0.0000000000 1.0000000000))
((0 . "LINE") (100 . "AcDbEntity") (67 . 0) (8 . "A-Window") (62 . 151) (6 . "Continuous") (100 . "AcDbLine") (10 997.4171111597 66.9194120805 0.0000000000) (11 997.4171111597 67.8129549452 0.0000000000) (210 0.0000000000 0.0000000000 1.0000000000))
((0 . "LINE") (100 . "AcDbEntity") (67 . 0) (8 . "A-Window") (62 . 151) (6 . "Continuous") (100 . "AcDbLine") (10 997.4171111597 61.9094120805 0.0000000000) (11 997.4171111597 62.8029549452 0.0000000000) (210 0.0000000000 0.0000000000 1.0000000000))
((0 . "LINE") (100 . "AcDbEntity") (67 . 0) (8 . "A-Window") (62 . 151) (6 . "Continuous") (100 . "AcDbLine") (10 997.4171111597 63.5794120805 0.0000000000) (11 997.4171111597 64.4729549452 0.0000000000) (210 0.0000000000 0.0000000000 1.0000000000))
((0 . "LINE") (100 . "AcDbEntity") (67 . 0) (8 . "A-Window") (62 . 151) (6 . "Continuous") (100 . "AcDbLine") (10 997.4171111597 65.2494120805 0.0000000000) (11 997.4171111597 66.1429549452 0.0000000000) (210 0.0000000000 0.0000000000 1.0000000000))
((0 . "LINE") (100 . "AcDbEntity") (67 . 0) (8 . "A-Window") (62 . 151) (6 . "Continuous") (100 . "AcDbLine") (10 997.4171111597 71.9294120805 0.0000000000) (11 997.4171111597 72.8229549452 0.0000000000) (210 0.0000000000 0.0000000000 1.0000000000))
((0 . "LINE") (100 . "AcDbEntity") (67 . 0) (8 . "A-Window") (62 . 151) (6 . "Continuous") (100 . "AcDbLine") (10 997.4171111597 70.2594120805 0.0000000000) (11 997.4171111597 71.1529549452 0.0000000000) (210 0.0000000000 0.0000000000 1.0000000000))
((0 . "LINE") (100 . "AcDbEntity") (67 . 0) (8 . "A-Window") (62 . 151) (6 . "Continuous") (100 . "AcDbLine") (10 997.4171111597 68.5894120805 0.0000000000) (11 997.4171111597 69.4829549452 0.0000000000) (210 0.0000000000 0.0000000000 1.0000000000))
((0 . "LINE") (100 . "AcDbEntity") (67 . 0) (8 . "A-Window") (62 . 151) (6 . "Continuous") (100 . "AcDbLine") (10 1001.8671111597 60.9396136866 0.0000000000) (11 1001.8671111597 61.8331565513 0.0000000000) (210 0.0000000000 0.0000000000 1.0000000000))
((0 . "LINE") (100 . "AcDbEntity") (67 . 0) (8 . "A-Window") (62 . 151) (6 . "Continuous") (100 . "AcDbLine") (10 1001.8671111597 65.9496136866 0.0000000000) (11 1001.8671111597 66.8431565513 0.0000000000) (210 0.0000000000 0.0000000000 1.0000000000))
((0 . "LINE") (100 . "AcDbEntity") (67 . 0) (8 . "A-Window") (62 . 151) (6 . "Continuous") (100 . "AcDbLine") (10 1001.8671111597 67.6196136866 0.0000000000) (11 1001.8671111597 68.5131565513 0.0000000000) (210 0.0000000000 0.0000000000 1.0000000000))
((0 . "LINE") (100 . "AcDbEntity") (67 . 0) (8 . "A-Window") (62 . 151) (6 . "Continuous") (100 . "AcDbLine") (10 1001.8671111597 62.6096136866 0.0000000000) (11 1001.8671111597 63.5031565513 0.0000000000) (210 0.0000000000 0.0000000000 1.0000000000))
((0 . "LINE") (100 . "AcDbEntity") (67 . 0) (8 . "A-Window") (62 . 151) (6 . "Continuous") (100 . "AcDbLine") (10 1001.8671111597 64.2796136866 0.0000000000) (11 1001.8671111597 65.1731565513 0.0000000000) (210 0.0000000000 0.0000000000 1.0000000000))
((0 . "LINE") (100 . "AcDbEntity") (67 . 0) (8 . "A-Window") (62 . 151) (6 . "Continuous") (100 . "AcDbLine") (10 1001.8671111597 69.2896136866 0.0000000000) (11 1001.8671111597 70.1831565513 0.0000000000) (210 0.0000000000 0.0000000000 1.0000000000))
((0 . "LINE") (100 . "AcDbEntity") (67 . 0) (8 . "A-Window") (62 . 151) (6 . "Continuous") (100 . "AcDbLine") (10 1001.8671111597 70.9596136866 0.0000000000) (11 1001.8671111597 71.8531565513 0.0000000000) (210 0.0000000000 0.0000000000 1.0000000000))
((0 . "LINE") (100 . "AcDbEntity") (67 . 0) (8 . "A-Window") (62 . 151) (6 . "Continuous") (100 . "AcDbLine") (10 1001.8671111597 72.6296136866 0.0000000000) (11 1001.8671111597 72.8917774718 0.0000000000) (210 0.0000000000 0.0000000000 1.0000000000))
((0 . "LINE") (100 . "AcDbEntity") (67 . 0) (8 . "A-Window") (62 . 151) (6 . "Continuous") (100 . "AcDbLine") (10 996.8921111597 63.1911835129 0.0000000000) (11 1002.3921111597 62.2213851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1001.8671111597 62.6096136866) (40 . 0.0000000000) (41 . 0.0000000000) (42 . 0.0000000000) (91 . 0) (10 1002.3921111597 62.2213851190) (40 . 0.0000000000) (41 . 0.0000000000) (42 . 0.0000000000) (91 . 0) (10 1001.8671111597 61.8331565513) (40 . 0.0000000000) (41 . 0.0000000000) (42 . 0.0000000000) (91 . 0) (10 997.4171111597 62.8029549452) (40 . 0.0000000000) (41 . 0.0000000000) (42 . 0.0000000000) (91 . 0) (10 996.8921111597 63.1911835129) (40 . 0.0000000000) (41 . 0.0000000000) (42 . 0.0000000000) (91 . 0) (10 997.4171111597 63.5794120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 996.8921111597 64.8611835129 0.0000000000) (11 1002.3921111597 63.8913851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1001.8671111597 64.2796136866) (40 . 0.0000000000) (41 . 0.0000000000) (42 . 0.0000000000) (91 . 0) (10 1002.3921111597 63.8913851190) (40 . 0.0000000000) (41 . 0.0000000000) (42 . 0.0000000000) (91 . 0) (10 1001.8671111597 63.5031565513) (40 . 0.0000000000) (41 . 0.0000000000) (42 . 0.0000000000) (91 . 0) (10 997.4171111597 64.4729549452) (40 . 0.0000000000) (41 . 0.0000000000) (42 . 0.0000000000) (91 . 0) (10 996.8921111597 64.8611835129) (40 . 0.0000000000) (41 . 0.0000000000) (42 . 0.0000000000) (91 . 0) (10 997.4171111597 65.2494120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 996.8921111597 66.5311835129 0.0000000000) (11 1002.3921111597 65.5613851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1001.8671111597 65.9496136866) (40 . 0.0000000000) (41 . 0.0000000000) (42 . 0.0000000000) (91 . 0) (10 1002.3921111597 65.5613851190) (40 . 0.0000000000) (41 . 0.0000000000) (42 . 0.0000000000) (91 . 0) (10 1001.8671111597 65.1731565513) (40 . 0.0000000000) (41 . 0.0000000000) (42 . 0.0000000000) (91 . 0) (10 997.4171111597 66.1429549452) (40 . 0.0000000000) (41 . 0.0000000000) (42 . 0.0000000000) (91 . 0) (10 996.8921111597 66.5311835129) (40 . 0.0000000000) (41 . 0.0000000000) (42 . 0.0000000000) (91 . 0) (10 997.4171111597 66.9194120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 996.8921111597 68.2011835129 0.0000000000) (11 1002.3921111597 67.2313851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1001.8671111597 67.6196136866) (40 . 0.0000000000) (41 . 0.0000000000) (42 . 0.0000000000) (91 . 0) (10 1002.3921111597 67.2313851190) (40 . 0.0000000000) (41 . 0.0000000000) (42 . 0.0000000000) (91 . 0) (10 1001.8671111597 66.8431565513) (40 . 0.0000000000) (41 . 0.0000000000) (42 . 0.0000000000) (91 . 0) (10 997.4171111597 67.8129549452) (40 . 0.0000000000) (41 . 0.0000000000) (42 . 0.0000000000) (91 . 0) (10 996.8921111597 68.2011835129) (40 . 0.0000000000) (41 . 0.0000000000) (42 . 0.0000000000) (91 . 0) (10 997.4171111597 68.5894120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 996.8921111597 69.8711835129 0.0000000000) (11 1002.3921111597 68.9013851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1001.8671111597 69.2896136866) (40 . 0.0000000000) (41 . 0.0000000000) (42 . 0.0000000000) (91 . 0) (10 1002.3921111597 68.9013851190) (40 . 0.0000000000) (41 . 0.0000000000) (42 . 0.0000000000) (91 . 0) (10 1001.8671111597 68.5131565513) (40 . 0.0000000000) (41 . 0.0000000000) (42 . 0.0000000000) (91 . 0) (10 997.4171111597 69.4829549452) (40 . 0.0000000000) (41 . 0.0000000000) (42 . 0.0000000000) (91 . 0) (10 996.8921111597 69.8711835129) (40 . 0.0000000000) (41 . 0.0000000000) (42 . 0.0000000000) (91 . 0) (10 997.4171111597 70.2594120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 996.8921111597 71.5411835129 0.0000000000) (11 1002.3921111597 70.5713851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1001.8671111597 70.9596136866) (40 . 0.0000000000) (41 . 0.0000000000) (42 . 0.0000000000) (91 . 0) (10 1002.3921111597 70.5713851190) (40 . 0.0000000000) (41 . 0.0000000000) (42 . 0.0000000000) (91 . 0) (10 1001.8671111597 70.1831565513) (40 . 0.0000000000) (41 . 0.0000000000) (42 . 0.0000000000) (91 . 0) (10 997.4171111597 71.1529549452) (40 . 0.0000000000) (41 . 0.0000000000) (42 . 0.0000000000) (91 . 0) (10 996.8921111597 71.5411835129) (40 . 0.0000000000) (41 . 0.0000000000) (42 . 0.0000000000) (91 . 0) (10 997.4171111597 71.9294120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 998.7035528336 72.8917774718 0.0000000000) (11 1002.3921111597 72.2413851190 0.0000000000) (210 0.0000000000 0.0000000000 1.0000000000))
((0 . "LWPOLYLINE") (100 . "AcDbEntity") (67 . 0) (8 . "A-Window") (62 . 151) (6 . "Continuous") (100 . "AcDbPolyline") (90 . 6) (70 . 0) (43 . 0.0000000000) (38 . 0.0000000000) (39 . 0.0000000000) (10 1000.6641509865 72.8917774718) (40 . 0.0000000000) (41 . 0.0000000000) (42 . 0.0000000000) (91 . 0) (10 1001.8671111597 72.6296136866) (40 . 0.0000000000) (41 . 0.0000000000) (42 . 0.0000000000) (91 . 0) (10 1002.3921111597 72.2413851190) (40 . 0.0000000000) (41 . 0.0000000000) (42 . 0.0000000000) (91 . 0) (10 1001.8671111597 71.8531565513) (40 . 0.0000000000) (41 . 0.0000000000) (42 . 0.0000000000) (91 . 0) (10 997.4171111597 72.8229549452) (40 . 0.0000000000) (41 . 0.0000000000) (42 . 0.0000000000) (91 . 0) (10 997.3240427215 72.8917774718) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 4) (70 . 1) (43 . 0.0000000000) (38 . 0.0000000000) (39 . 0.0000000000) (10 994.1421111597 73.8917774718) (40 . 0.0000000000) (41 . 0.0000000000) (42 . 0.0000000000) (91 . 0) (10 994.1421111597 72.8917774718) (40 . 0.0000000000) (41 . 0.0000000000) (42 . 0.0000000000) (91 . 0) (10 1005.1421111597 72.8917774718) (40 . 0.0000000000) (41 . 0.0000000000) (42 . 0.0000000000) (91 . 0) (10 1005.1421111597 73.8917774718) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 996.8921111597 61.5211835129 0.0000000000) (11 1002.3921111597 63.5513851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1001.8671111597 60.9396136866) (40 . 0.0000000000) (41 . 0.0000000000) (42 . 0.0000000000) (91 . 0) (10 1002.3921111597 63.5513851190) (40 . 0.0000000000) (41 . 0.0000000000) (42 . 0.0000000000) (91 . 0) (10 1001.8671111597 63.1631565513) (40 . 0.0000000000) (41 . 0.0000000000) (42 . 0.0000000000) (91 . 0) (10 997.4171111597 61.1329549452) (40 . 0.0000000000) (41 . 0.0000000000) (42 . 0.0000000000) (91 . 0) (10 996.8921111597 61.5211835129) (40 . 0.0000000000) (41 . 0.0000000000) (42 . 0.0000000000) (91 . 0) (10 997.4171111597 61.9094120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 997.4171111597 63.2394120805 0.0000000000) (11 997.4171111597 61.1329549452 0.0000000000) (210 0.0000000000 0.0000000000 1.0000000000))
((0 . "LINE") (100 . "AcDbEntity") (67 . 0) (8 . "A-Window") (62 . 151) (6 . "Continuous") (100 . "AcDbLine") (10 996.1780095446 78.2917774718 0.0000000000) (11 1003.1062127748 78.2917774718 0.0000000000) (210 0.0000000000 0.0000000000 1.0000000000))
((0 . "LINE") (100 . "AcDbEntity") (67 . 0) (8 . "A-Window") (62 . 151) (6 . "CENTER2") (100 . "AcDbLine") (10 999.6421111597 37.5451762388 0.0000000000) (11 999.6421111597 81.5869711621 0.0000000000) (210 0.0000000000 0.0000000000 1.0000000000))
((0 . "LINE") (100 . "AcDbEntity") (67 . 0) (8 . "A-Window") (62 . 151) (6 . "Continuous") (100 . "AcDbLine") (10 997.3327100830 77.2917774717 0.0000000000) (11 997.3327100830 73.8917774718 0.0000000000) (210 0.0000000000 0.0000000000 1.0000000000))
((0 . "LINE") (100 . "AcDbEntity") (67 . 0) (8 . "A-Window") (62 . 151) (6 . "Continuous") (100 . "AcDbLine") (10 1001.9515122365 77.2917774717 0.0000000000) (11 1001.9515122365 73.8917774718 0.0000000000) (210 0.0000000000 0.0000000000 1.0000000000))
((0 . "LWPOLYLINE") (100 . "AcDbEntity") (67 . 0) (8 . "A-Window") (62 . 151) (6 . "Continuous") (100 . "AcDbPolyline") (90 . 6) (70 . 0) (43 . 0.0000000000) (38 . 0.0000000000) (39 . 0.0000000000) (10 1004.2609133132 73.8917774718) (40 . 0.0000000000) (41 . 0.0000000000) (42 . 0.0000000000) (91 . 0) (10 1004.2609133132 77.2917774717) (40 . 0.0000000000) (41 . 0.0000000000) (42 . 0.8660254038) (91 . 0) (10 1001.9515122365 77.2917774717) (40 . 0.0000000000) (41 . 0.0000000000) (42 . 0.4330127019) (91 . 0) (10 997.3327100830 77.2917774717) (40 . 0.0000000000) (41 . 0.0000000000) (42 . 0.8660254038) (91 . 0) (10 995.0233090062 77.2917774717) (40 . 0.0000000000) (41 . 0.0000000000) (42 . 0.0000000000) (91 . 0) (10 995.0233090062 73.8917774718) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 4) (70 . 1) (43 . 0.0000000000) (38 . 0.0000000000) (39 . 0.0000000000) (10 997.4171111597 42.6957453328) (40 . 0.0000000000) (41 . 0.0000000000) (42 . 0.0000000000) (91 . 0) (10 999.0286768980 42.5675818646) (40 . 0.0000000000) (41 . 0.0000000000) (42 . 0.0000000000) (91 . 0) (10 997.4171111597 43.0839739004) (40 . 0.0000000000) (41 . 0.0000000000) (42 . 0.0000000000) (91 . 0) (10 997.2096111597 42.8898596166) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 997.2096111597 42.8898596166 0.0000000000) (11 999.0286768980 42.5675818646 0.0000000000) (210 0.0000000000 0.0000000000 1.0000000000))
((0 . "LINE") (100 . "AcDbEntity") (67 . 0) (8 . "A-Window") (62 . 151) (6 . "Continuous") (100 . "AcDbLine") (10 997.4171111597 48.2094120805 0.0000000000) (11 997.4171111597 49.1029549452 0.0000000000) (210 0.0000000000 0.0000000000 1.0000000000))
((0 . "LINE") (100 . "AcDbEntity") (67 . 0) (8 . "A-Window") (62 . 151) (6 . "Continuous") (100 . "AcDbLine") (10 997.4171111597 56.5594120805 0.0000000000) (11 997.4171111597 57.4529549452 0.0000000000) (210 0.0000000000 0.0000000000 1.0000000000))
((0 . "LINE") (100 . "AcDbEntity") (67 . 0) (8 . "A-Window") (62 . 151) (6 . "Continuous") (100 . "AcDbLine") (10 997.1058611597 44.5782406548 0.0000000000) (11 998.3789500210 44.3526917877 0.0000000000) (210 0.0000000000 0.0000000000 1.0000000000))
((0 . "LINE") (100 . "AcDbEntity") (67 . 0) (8 . "A-Window") (62 . 151) (6 . "Continuous") (100 . "AcDbLine") (10 997.4171111597 44.8694120805 0.0000000000) (11 997.4171111597 45.7629549452 0.0000000000) (210 0.0000000000 0.0000000000 1.0000000000))
((0 . "LWPOLYLINE") (100 . "AcDbEntity") (67 . 0) (8 . "A-Window") (62 . 151) (6 . "Continuous") (100 . "AcDbPolyline") (90 . 5) (70 . 0) (43 . 0.0000000000) (38 . 0.0000000000) (39 . 0.0000000000) (10 998.4889750699 44.0504004504) (40 . 0.0000000000) (41 . 0.0000000000) (42 . 0.0000000000) (91 . 0) (10 997.4171111597 44.2870692290) (40 . 0.0000000000) (41 . 0.0000000000) (42 . 0.0000000000) (91 . 0) (10 997.1058611597 44.5782406548) (40 . 0.0000000000) (41 . 0.0000000000) (42 . 0.0000000000) (91 . 0) (10 997.4171111597 44.8694120805) (40 . 0.0000000000) (41 . 0.0000000000) (42 . 0.0000000000) (91 . 0) (10 998.2584972452 44.6836330695) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 997.4171111597 46.5394120805 0.0000000000) (11 997.4171111597 47.4329549452 0.0000000000) (210 0.0000000000 0.0000000000 1.0000000000))
((0 . "LINE") (100 . "AcDbEntity") (67 . 0) (8 . "A-Window") (62 . 151) (6 . "Continuous") (100 . "AcDbLine") (10 997.4171111597 43.0839739004 0.0000000000) (11 997.4171111597 44.2870692290 0.0000000000) (210 0.0000000000 0.0000000000 1.0000000000))
((0 . "LINE") (100 . "AcDbEntity") (67 . 0) (8 . "A-Window") (62 . 151) (6 . "Continuous") (100 . "AcDbLine") (10 1001.8671111597 44.1620742983 0.0000000000) (11 1001.8671111597 44.7931565513 0.0000000000) (210 0.0000000000 0.0000000000 1.0000000000))
((0 . "LINE") (100 . "AcDbEntity") (67 . 0) (8 . "A-Window") (62 . 151) (6 . "Continuous") (100 . "AcDbLine") (10 1001.8671111597 45.5696136866 0.0000000000) (11 1001.8671111597 46.4631565513 0.0000000000) (210 0.0000000000 0.0000000000 1.0000000000))
((0 . "LINE") (100 . "AcDbEntity") (67 . 0) (8 . "A-Window") (62 . 151) (6 . "Continuous") (100 . "AcDbLine") (10 1001.8671111597 47.2396136866 0.0000000000) (11 1001.8671111597 48.1331565513 0.0000000000) (210 0.0000000000 0.0000000000 1.0000000000))
((0 . "LINE") (100 . "AcDbEntity") (67 . 0) (8 . "A-Window") (62 . 151) (6 . "Continuous") (100 . "AcDbLine") (10 1001.8671111597 57.2596136866 0.0000000000) (11 1001.8671111597 58.1531565513 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1001.8671111597 45.5696136866) (40 . 0.0000000000) (41 . 0.0000000000) (42 . 0.0000000000) (91 . 0) (10 1002.3921111597 45.1813851190) (40 . 0.0000000000) (41 . 0.0000000000) (42 . 0.0000000000) (91 . 0) (10 1001.8671111597 44.7931565513) (40 . 0.0000000000) (41 . 0.0000000000) (42 . 0.0000000000) (91 . 0) (10 997.4171111597 45.7629549452) (40 . 0.0000000000) (41 . 0.0000000000) (42 . 0.0000000000) (91 . 0) (10 996.8921111597 46.1511835129) (40 . 0.0000000000) (41 . 0.0000000000) (42 . 0.0000000000) (91 . 0) (10 997.4171111597 46.5394120805) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1001.8671111597 55.5896136866) (40 . 0.0000000000) (41 . 0.0000000000) (42 . 0.0000000000) (91 . 0) (10 1002.3921111597 55.2013851190) (40 . 0.0000000000) (41 . 0.0000000000) (42 . 0.0000000000) (91 . 0) (10 1001.8671111597 54.8131565513) (40 . 0.0000000000) (41 . 0.0000000000) (42 . 0.0000000000) (91 . 0) (10 997.4171111597 55.7829549452) (40 . 0.0000000000) (41 . 0.0000000000) (42 . 0.0000000000) (91 . 0) (10 996.8921111597 56.1711835129) (40 . 0.0000000000) (41 . 0.0000000000) (42 . 0.0000000000) (91 . 0) (10 997.4171111597 56.5594120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 996.8921111597 47.8211835129 0.0000000000) (11 1002.3921111597 46.8513851190 0.0000000000) (210 0.0000000000 0.0000000000 1.0000000000))
((0 . "LINE") (100 . "AcDbEntity") (67 . 0) (8 . "A-Window") (62 . 151) (6 . "Continuous") (100 . "AcDbLine") (10 996.8921111597 56.1711835129 0.0000000000) (11 1002.3921111597 55.2013851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1001.8671111597 47.2396136866) (40 . 0.0000000000) (41 . 0.0000000000) (42 . 0.0000000000) (91 . 0) (10 1002.3921111597 46.8513851190) (40 . 0.0000000000) (41 . 0.0000000000) (42 . 0.0000000000) (91 . 0) (10 1001.8671111597 46.4631565513) (40 . 0.0000000000) (41 . 0.0000000000) (42 . 0.0000000000) (91 . 0) (10 997.4171111597 47.4329549452) (40 . 0.0000000000) (41 . 0.0000000000) (42 . 0.0000000000) (91 . 0) (10 996.8921111597 47.8211835129) (40 . 0.0000000000) (41 . 0.0000000000) (42 . 0.0000000000) (91 . 0) (10 997.4171111597 48.2094120805) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1001.8671111597 57.2596136866) (40 . 0.0000000000) (41 . 0.0000000000) (42 . 0.0000000000) (91 . 0) (10 1002.3921111597 56.8713851190) (40 . 0.0000000000) (41 . 0.0000000000) (42 . 0.0000000000) (91 . 0) (10 1001.8671111597 56.4831565513) (40 . 0.0000000000) (41 . 0.0000000000) (42 . 0.0000000000) (91 . 0) (10 997.4171111597 57.4529549452) (40 . 0.0000000000) (41 . 0.0000000000) (42 . 0.0000000000) (91 . 0) (10 996.8921111597 57.8411835128) (40 . 0.0000000000) (41 . 0.0000000000) (42 . 0.0000000000) (91 . 0) (10 997.4171111597 58.2294120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 996.8921111597 57.8411835128 0.0000000000) (11 1002.3921111597 56.8713851190 0.0000000000) (210 0.0000000000 0.0000000000 1.0000000000))
((0 . "LINE") (100 . "AcDbEntity") (67 . 0) (8 . "A-Window") (62 . 151) (6 . "Continuous") (100 . "AcDbLine") (10 996.8921111597 46.1511835129 0.0000000000) (11 1002.3921111597 45.1813851190 0.0000000000) (210 0.0000000000 0.0000000000 1.0000000000))
((0 . "LWPOLYLINE") (100 . "AcDbEntity") (67 . 0) (8 . "A-Window") (62 . 151) (6 . "Continuous") (100 . "AcDbPolyline") (90 . 10) (70 . 0) (43 . 0.0000000000) (38 . 0.0000000000) (39 . 0.0000000000) (10 997.4171111597 42.6957453328) (40 . 0.0000000000) (41 . 0.0000000000) (42 . 0.0000000000) (91 . 0) (10 997.4171111597 41.0687741511) (40 . 0.0000000000) (41 . 0.0000000000) (42 . 0.0000000000) (91 . 0) (10 999.6421111597 39.2017774718) (40 . 0.0000000000) (41 . 0.0000000000) (42 . 0.0000000000) (91 . 0) (10 1001.8671111597 41.0687741511) (40 . 0.0000000000) (41 . 0.0000000000) (42 . 0.0000000000) (91 . 0) (10 1001.8671111597 43.5797314468) (40 . 0.0000000000) (41 . 0.0000000000) (42 . 0.0000000000) (91 . 0) (10 1002.1783611597 43.8709028725) (40 . 0.0000000000) (41 . 0.0000000000) (42 . 0.0000000000) (91 . 0) (10 1001.8671111597 44.1620742983) (40 . 0.0000000000) (41 . 0.0000000000) (42 . 0.2138820884) (91 . 0) (10 998.2584972452 44.6836330695) (40 . 0.0000000000) (41 . 0.0000000000) (42 . 0.0000000000) (91 . 0) (10 1000.1106379993 39.5949181700) (40 . 0.0000000000) (41 . 0.0000000000) (42 . 0.2315249815) (91 . 0) (10 997.4171111597 41.0687741511) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 997.4171111597 59.8994120805 0.0000000000) (11 997.4171111597 60.7929549452 0.0000000000) (210 0.0000000000 0.0000000000 1.0000000000))
((0 . "LINE") (100 . "AcDbEntity") (67 . 0) (8 . "A-Window") (62 . 151) (6 . "Continuous") (100 . "AcDbLine") (10 997.4171111597 61.5694120805 0.0000000000) (11 997.4171111597 62.4629549452 0.0000000000) (210 0.0000000000 0.0000000000 1.0000000000))
((0 . "LINE") (100 . "AcDbEntity") (67 . 0) (8 . "A-Window") (62 . 151) (6 . "Continuous") (100 . "AcDbLine") (10 997.4171111597 63.2394120805 0.0000000000) (11 997.4171111597 61.1329549452 0.0000000000) (210 0.0000000000 0.0000000000 1.0000000000))
((0 . "LINE") (100 . "AcDbEntity") (67 . 0) (8 . "A-Window") (62 . 151) (6 . "Continuous") (100 . "AcDbLine") (10 1001.8671111597 58.9296136866 0.0000000000) (11 1001.8671111597 59.8231565513 0.0000000000) (210 0.0000000000 0.0000000000 1.0000000000))
((0 . "LINE") (100 . "AcDbEntity") (67 . 0) (8 . "A-Window") (62 . 151) (6 . "Continuous") (100 . "AcDbLine") (10 1001.8671111597 60.5996136866 0.0000000000) (11 1001.8671111597 61.4931565513 0.0000000000) (210 0.0000000000 0.0000000000 1.0000000000))
((0 . "LINE") (100 . "AcDbEntity") (67 . 0) (8 . "A-Window") (62 . 151) (6 . "Continuous") (100 . "AcDbLine") (10 1001.8671111597 62.2696136866 0.0000000000) (11 1001.8671111597 63.1631565513 0.0000000000) (210 0.0000000000 0.0000000000 1.0000000000))
((0 . "LINE") (100 . "AcDbEntity") (67 . 0) (8 . "A-Window") (62 . 151) (6 . "Continuous") (100 . "AcDbLine") (10 996.8921111597 61.1811835129 0.0000000000) (11 1002.3921111597 60.2113851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1001.8671111597 60.5996136866) (40 . 0.0000000000) (41 . 0.0000000000) (42 . 0.0000000000) (91 . 0) (10 1002.3921111597 60.2113851190) (40 . 0.0000000000) (41 . 0.0000000000) (42 . 0.0000000000) (91 . 0) (10 1001.8671111597 59.8231565513) (40 . 0.0000000000) (41 . 0.0000000000) (42 . 0.0000000000) (91 . 0) (10 997.4171111597 60.7929549452) (40 . 0.0000000000) (41 . 0.0000000000) (42 . 0.0000000000) (91 . 0) (10 996.8921111597 61.1811835129) (40 . 0.0000000000) (41 . 0.0000000000) (42 . 0.0000000000) (91 . 0) (10 997.4171111597 61.5694120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 996.8921111597 62.8511835129 0.0000000000) (11 1002.3921111597 61.8813851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1001.8671111597 62.2696136866) (40 . 0.0000000000) (41 . 0.0000000000) (42 . 0.0000000000) (91 . 0) (10 1002.3921111597 61.8813851190) (40 . 0.0000000000) (41 . 0.0000000000) (42 . 0.0000000000) (91 . 0) (10 1001.8671111597 61.4931565513) (40 . 0.0000000000) (41 . 0.0000000000) (42 . 0.0000000000) (91 . 0) (10 997.4171111597 62.4629549452) (40 . 0.0000000000) (41 . 0.0000000000) (42 . 0.0000000000) (91 . 0) (10 996.8921111597 62.8511835129) (40 . 0.0000000000) (41 . 0.0000000000) (42 . 0.0000000000) (91 . 0) (10 997.4171111597 63.2394120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 996.8921111597 61.5211835129 0.0000000000) (11 1002.3921111597 63.5513851190 0.0000000000) (210 0.0000000000 0.0000000000 1.0000000000))
((0 . "LINE") (100 . "AcDbEntity") (67 . 0) (8 . "A-Window") (62 . 151) (6 . "Continuous") (100 . "AcDbLine") (10 996.8921111597 59.5111835129 0.0000000000) (11 1002.3921111597 58.5413851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1001.8671111597 58.9296136866) (40 . 0.0000000000) (41 . 0.0000000000) (42 . 0.0000000000) (91 . 0) (10 1002.3921111597 58.5413851190) (40 . 0.0000000000) (41 . 0.0000000000) (42 . 0.0000000000) (91 . 0) (10 1001.8671111597 58.1531565513) (40 . 0.0000000000) (41 . 0.0000000000) (42 . 0.0000000000) (91 . 0) (10 997.4171111597 59.1229549452) (40 . 0.0000000000) (41 . 0.0000000000) (42 . 0.0000000000) (91 . 0) (10 996.8921111597 59.5111835129) (40 . 0.0000000000) (41 . 0.0000000000) (42 . 0.0000000000) (91 . 0) (10 997.4171111597 59.8994120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 997.4171111597 58.2294120805 0.0000000000) (11 997.4171111597 59.1229549452 0.0000000000) (210 0.0000000000 0.0000000000 1.0000000000))
((0 . "LINE") (100 . "AcDbEntity") (67 . 0) (8 . "A-Window") (62 . 151) (6 . "Continuous") (100 . "AcDbLine") (10 997.4171111597 54.8894120805 0.0000000000) (11 997.4171111597 55.7829549452 0.0000000000) (210 0.0000000000 0.0000000000 1.0000000000))
((0 . "LINE") (100 . "AcDbEntity") (67 . 0) (8 . "A-Window") (62 . 151) (6 . "Continuous") (100 . "AcDbLine") (10 1001.8671111597 53.9196136866 0.0000000000) (11 1001.8671111597 54.8131565513 0.0000000000) (210 0.0000000000 0.0000000000 1.0000000000))
((0 . "LINE") (100 . "AcDbEntity") (67 . 0) (8 . "A-Window") (62 . 151) (6 . "Continuous") (100 . "AcDbLine") (10 997.4171111597 54.8894120805 0.0000000000) (11 997.4171111597 55.7829549452 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1001.8671111597 53.9196136866) (40 . 0.0000000000) (41 . 0.0000000000) (42 . 0.0000000000) (91 . 0) (10 1002.3921111597 53.5313851190) (40 . 0.0000000000) (41 . 0.0000000000) (42 . 0.0000000000) (91 . 0) (10 1001.8671111597 53.1431565513) (40 . 0.0000000000) (41 . 0.0000000000) (42 . 0.0000000000) (91 . 0) (10 997.4171111597 54.1129549452) (40 . 0.0000000000) (41 . 0.0000000000) (42 . 0.0000000000) (91 . 0) (10 996.8921111597 54.5011835129) (40 . 0.0000000000) (41 . 0.0000000000) (42 . 0.0000000000) (91 . 0) (10 997.4171111597 54.8894120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 996.8921111597 54.5011835129 0.0000000000) (11 1002.3921111597 53.5313851190 0.0000000000) (210 0.0000000000 0.0000000000 1.0000000000))
((0 . "LINE") (100 . "AcDbEntity") (67 . 0) (8 . "A-Window") (62 . 151) (6 . "Continuous") (100 . "AcDbLine") (10 997.4171111597 53.2194120805 0.0000000000) (11 997.4171111597 54.1129549452 0.0000000000) (210 0.0000000000 0.0000000000 1.0000000000))
((0 . "LINE") (100 . "AcDbEntity") (67 . 0) (8 . "A-Window") (62 . 151) (6 . "Continuous") (100 . "AcDbLine") (10 1001.8671111597 52.2496136866 0.0000000000) (11 1001.8671111597 53.1431565513 0.0000000000) (210 0.0000000000 0.0000000000 1.0000000000))
((0 . "LINE") (100 . "AcDbEntity") (67 . 0) (8 . "A-Window") (62 . 151) (6 . "Continuous") (100 . "AcDbLine") (10 997.4171111597 53.2194120805 0.0000000000) (11 997.4171111597 54.1129549452 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1001.8671111597 52.2496136866) (40 . 0.0000000000) (41 . 0.0000000000) (42 . 0.0000000000) (91 . 0) (10 1002.3921111597 51.8613851190) (40 . 0.0000000000) (41 . 0.0000000000) (42 . 0.0000000000) (91 . 0) (10 1001.8671111597 51.4731565513) (40 . 0.0000000000) (41 . 0.0000000000) (42 . 0.0000000000) (91 . 0) (10 997.4171111597 52.4429549452) (40 . 0.0000000000) (41 . 0.0000000000) (42 . 0.0000000000) (91 . 0) (10 996.8921111597 52.8311835129) (40 . 0.0000000000) (41 . 0.0000000000) (42 . 0.0000000000) (91 . 0) (10 997.4171111597 53.2194120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 996.8921111597 52.8311835129 0.0000000000) (11 1002.3921111597 51.8613851190 0.0000000000) (210 0.0000000000 0.0000000000 1.0000000000))
((0 . "LINE") (100 . "AcDbEntity") (67 . 0) (8 . "A-Window") (62 . 151) (6 . "Continuous") (100 . "AcDbLine") (10 992.6421111597 71.3967000000 0.0000000000) (11 991.1421111597 71.3967000000 0.0000000000) (210 0.0000000000 0.0000000000 1.0000000000))
((0 . "LINE") (100 . "AcDbEntity") (67 . 0) (8 . "A-Window") (62 . 151) (6 . "Continuous") (100 . "AcDbLine") (10 992.6421111597 72.8917774718 0.0000000000) (11 992.6421111597 71.3967000000 0.0000000000) (210 0.0000000000 0.0000000000 1.0000000000))
((0 . "LINE") (100 . "AcDbEntity") (67 . 0) (8 . "A-Window") (62 . 151) (6 . "Continuous") (100 . "AcDbLine") (10 994.1822728731 72.8917774718 0.0000000000) (11 992.6421111597 72.8917774718 0.0000000000) (210 0.0000000000 0.0000000000 1.0000000000))
((0 . "LINE") (100 . "AcDbEntity") (67 . 0) (8 . "A-Window") (62 . 151) (6 . "Continuous") (100 . "AcDbLine") (10 1006.6421111597 71.3967000000 0.0000000000) (11 1006.6421111597 72.8917774718 0.0000000000) (210 0.0000000000 0.0000000000 1.0000000000))
((0 . "LINE") (100 . "AcDbEntity") (67 . 0) (8 . "A-Window") (62 . 151) (6 . "Continuous") (100 . "AcDbLine") (10 1008.1421111597 71.3967000000 0.0000000000) (11 1006.6421111597 71.3967000000 0.0000000000) (210 0.0000000000 0.0000000000 1.0000000000))
((0 . "LWPOLYLINE") (100 . "AcDbEntity") (67 . 0) (8 . "A-Window") (62 . 151) (6 . "Continuous") (100 . "AcDbPolyline") (90 . 4) (70 . 1) (43 . 0.0000000000) (38 . 0.0000000000) (39 . 0.0000000000) (10 992.6421111597 71.3967000000) (40 . 0.0000000000) (41 . 0.0000000000) (42 . 0.0000000000) (91 . 0) (10 1006.6421111597 71.3967000000) (40 . 0.0000000000) (41 . 0.0000000000) (42 . 0.0000000000) (91 . 0) (10 1006.6421111597 72.8917774718) (40 . 0.0000000000) (41 . 0.0000000000) (42 . 0.0000000000) (91 . 0) (10 992.6421111597 72.8917774718) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 997.4171111597 51.5494120805 0.0000000000) (11 997.4171111597 52.4429549452 0.0000000000) (210 0.0000000000 0.0000000000 1.0000000000))
((0 . "LINE") (100 . "AcDbEntity") (67 . 0) (8 . "A-Window") (62 . 151) (6 . "Continuous") (100 . "AcDbLine") (10 1001.8671111597 50.5796136866 0.0000000000) (11 1001.8671111597 51.4731565513 0.0000000000) (210 0.0000000000 0.0000000000 1.0000000000))
((0 . "LINE") (100 . "AcDbEntity") (67 . 0) (8 . "A-Window") (62 . 151) (6 . "Continuous") (100 . "AcDbLine") (10 997.4171111597 51.5494120805 0.0000000000) (11 997.4171111597 52.4429549452 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1001.8671111597 50.5796136866) (40 . 0.0000000000) (41 . 0.0000000000) (42 . 0.0000000000) (91 . 0) (10 1002.3921111597 50.1913851190) (40 . 0.0000000000) (41 . 0.0000000000) (42 . 0.0000000000) (91 . 0) (10 1001.8671111597 49.8031565513) (40 . 0.0000000000) (41 . 0.0000000000) (42 . 0.0000000000) (91 . 0) (10 997.4171111597 50.7729549452) (40 . 0.0000000000) (41 . 0.0000000000) (42 . 0.0000000000) (91 . 0) (10 996.8921111597 51.1611835129) (40 . 0.0000000000) (41 . 0.0000000000) (42 . 0.0000000000) (91 . 0) (10 997.4171111597 51.5494120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 996.8921111597 51.1611835129 0.0000000000) (11 1002.3921111597 50.1913851190 0.0000000000) (210 0.0000000000 0.0000000000 1.0000000000))
((0 . "LINE") (100 . "AcDbEntity") (67 . 0) (8 . "A-Window") (62 . 151) (6 . "Continuous") (100 . "AcDbLine") (10 997.4171111597 49.8794120805 0.0000000000) (11 997.4171111597 50.7729549452 0.0000000000) (210 0.0000000000 0.0000000000 1.0000000000))
((0 . "LINE") (100 . "AcDbEntity") (67 . 0) (8 . "A-Window") (62 . 151) (6 . "Continuous") (100 . "AcDbLine") (10 1001.8671111597 48.9096136866 0.0000000000) (11 1001.8671111597 49.8031565513 0.0000000000) (210 0.0000000000 0.0000000000 1.0000000000))
((0 . "LINE") (100 . "AcDbEntity") (67 . 0) (8 . "A-Window") (62 . 151) (6 . "Continuous") (100 . "AcDbLine") (10 997.4171111597 49.8794120805 0.0000000000) (11 997.4171111597 50.7729549452 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1001.8671111597 48.9096136866) (40 . 0.0000000000) (41 . 0.0000000000) (42 . 0.0000000000) (91 . 0) (10 1002.3921111597 48.5213851190) (40 . 0.0000000000) (41 . 0.0000000000) (42 . 0.0000000000) (91 . 0) (10 1001.8671111597 48.1331565513) (40 . 0.0000000000) (41 . 0.0000000000) (42 . 0.0000000000) (91 . 0) (10 997.4171111597 49.1029549452) (40 . 0.0000000000) (41 . 0.0000000000) (42 . 0.0000000000) (91 . 0) (10 996.8921111597 49.4911835129) (40 . 0.0000000000) (41 . 0.0000000000) (42 . 0.0000000000) (91 . 0) (10 997.4171111597 49.8794120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 996.8921111597 49.4911835129 0.0000000000) (11 1002.3921111597 48.5213851190 0.0000000000) (210 0.0000000000 0.0000000000 1.0000000000))
((0 . "ARC") (100 . "AcDbEntity") (67 . 0) (8 . "A-Window") (62 . 151) (6 . "Continuous") (100 . "AcDbCircle") (10 1042.8123962019 66.7859023315 0.0000000000) (40 . 10.6781898097) (210 0.0000000000 0.0000000000 1.0000000000) (100 . "AcDbArc") (50 . 3.1031124361) (51 . -2.7687983156))
((0 . "LWPOLYLINE") (100 . "AcDbEntity") (67 . 0) (8 . "A-Window") (62 . 151) (6 . "Continuous") (370 . -3) (100 . "AcDbPolyline") (90 . 7) (70 . 0) (43 . 0.0000000000) (38 . 0.0000000000) (39 . 0.0000000000) (10 987.8889377023 31.0817739862) (40 . 0.0000000000) (41 . 0.0000000000) (42 . 0.0000000000) (91 . 0) (10 988.5701053708 31.2693893928) (40 . 0.0000000000) (41 . 0.0000000000) (42 . 0.0000000000) (91 . 0) (10 987.8889377023 32.1851406910) (40 . 0.0000000000) (41 . 0.0000000000) (42 . 0.0000000000) (91 . 0) (10 984.5310052066 33.7798758823) (40 . 0.0000000000) (41 . 0.0000000000) (42 . 0.0000000000) (91 . 0) (10 983.8498375381 33.7922604757) (40 . 0.0000000000) (41 . 0.0000000000) (42 . 0.0000000000) (91 . 0) (10 984.5310052066 32.8765091775) (40 . 0.0000000000) (41 . 0.0000000000) (42 . 0.0000000000) (91 . 0) (10 987.9028130501 31.0743579422) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (370 . -3) (100 . "AcDbPolyline") (90 . 2) (70 . 0) (43 . 0.0000000000) (38 . 0.0000000000) (39 . 0.0000000000) (10 988.5701053708 31.2693893928) (40 . 0.0000000000) (41 . 0.0000000000) (42 . 0.0000000000) (91 . 0) (10 983.8498375381 33.7922604757) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (370 . -3) (100 . "AcDbPolyline") (90 . 2) (70 . 0) (43 . 0.0000000000) (38 . 0.0000000000) (39 . 0.0000000000) (10 987.9816095952 21.4597508267) (40 . 0.0000000000) (41 . 0.0000000000) (42 . 0.0000000000) (91 . 0) (10 984.0685556388 23.5511852584) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (370 . -3) (100 . "AcDbPolyline") (90 . 5) (70 . 0) (43 . 0.0000000000) (38 . 0.0000000000) (39 . 0.0000000000) (10 983.8658658497 27.0637825200) (40 . 0.0000000000) (41 . 0.0000000000) (42 . 0.0000000000) (91 . 0) (10 984.5470335183 27.2513979266) (40 . 0.0000000000) (41 . 0.0000000000) (42 . 0.0000000000) (91 . 0) (10 987.9049660139 25.4566627353) (40 . 0.0000000000) (41 . 0.0000000000) (42 . 0.0000000000) (91 . 0) (10 988.5861336825 24.5409114371) (40 . 0.0000000000) (41 . 0.0000000000) (42 . 0.0000000000) (91 . 0) (10 987.9049660139 24.3532960304) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (370 . -3) (100 . "AcDbPolyline") (90 . 4) (70 . 0) (43 . 0.0000000000) (38 . 0.0000000000) (39 . 0.0000000000) (10 987.9188413617 24.3458799865) (40 . 0.0000000000) (41 . 0.0000000000) (42 . 0.0000000000) (91 . 0) (10 984.5470335183 26.1480312217) (40 . 0.0000000000) (41 . 0.0000000000) (42 . 0.0000000000) (91 . 0) (10 983.8658658497 27.0637825200) (40 . 0.0000000000) (41 . 0.0000000000) (42 . 0.0000000000) (91 . 0) (10 988.5861336825 24.5409114371) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (370 . -3) (100 . "AcDbPolyline") (90 . 2) (70 . 0) (43 . 0.0000000000) (38 . 0.0000000000) (39 . 0.0000000000) (10 987.9049660139 27.6694253066) (40 . 0.0000000000) (41 . 0.0000000000) (42 . 0.0000000000) (91 . 0) (10 988.5861336825 27.8570407132) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (370 . -3) (100 . "AcDbPolyline") (90 . 7) (70 . 0) (43 . 0.0000000000) (38 . 0.0000000000) (39 . 0.0000000000) (10 983.8658658497 30.3799117961) (40 . 0.0000000000) (41 . 0.0000000000) (42 . 0.0000000000) (91 . 0) (10 988.5861336825 27.8570407132) (40 . 0.0000000000) (41 . 0.0000000000) (42 . 0.0000000000) (91 . 0) (10 987.9049660139 28.7727920115) (40 . 0.0000000000) (41 . 0.0000000000) (42 . 0.0000000000) (91 . 0) (10 984.5470335183 30.5675272028) (40 . 0.0000000000) (41 . 0.0000000000) (42 . 0.0000000000) (91 . 0) (10 983.8658658497 30.3799117961) (40 . 0.0000000000) (41 . 0.0000000000) (42 . 0.0000000000) (91 . 0) (10 984.5470335183 29.4641604979) (40 . 0.0000000000) (41 . 0.0000000000) (42 . 0.0000000000) (91 . 0) (10 987.9188413617 27.6620092627) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (370 . -3) (100 . "AcDbPolyline") (90 . 7) (70 . 0) (43 . 0.0000000000) (38 . 0.0000000000) (39 . 0.0000000000) (10 984.7334070635 23.7561959660) (40 . 0.0000000000) (41 . 0.0000000000) (42 . 0.0000000000) (91 . 0) (10 984.0522393950 23.5685805594) (40 . 0.0000000000) (41 . 0.0000000000) (42 . 0.0000000000) (91 . 0) (10 985.1062221511 22.4448937926) (40 . 0.0000000000) (41 . 0.0000000000) (42 . 0.0000000000) (91 . 0) (10 986.9926852832 21.4366240389) (40 . 0.0000000000) (41 . 0.0000000000) (42 . 0.0000000000) (91 . 0) (10 987.9816095952 21.4597508267) (40 . 0.0000000000) (41 . 0.0000000000) (42 . 0.0000000000) (91 . 0) (10 987.3004419266 22.3755021249) (40 . 0.0000000000) (41 . 0.0000000000) (42 . 0.0000000000) (91 . 0) (10 984.7226963992 23.7532459058) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (370 . -3) (100 . "AcDbPolyline") (90 . 2) (70 . 0) (43 . 0.0000000000) (38 . 0.0000000000) (39 . 0.0000000000) (10 990.2320082673 35.4966999996) (40 . 0.0000000000) (41 . 0.0000000000) (42 . 0.0000000000) (91 . 0) (10 990.2320082673 36.5591518613) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 5) (70 . 1) (43 . 0.0000000000) (38 . 0.0000000000) (39 . 0.0000000000) (10 984.5291468612 24.3384639426) (40 . 0.0000000000) (41 . 0.0000000000) (42 . 0.0000000000) (91 . 0) (10 984.5451751729 35.4966999996) (40 . 0.0000000000) (41 . 0.0000000000) (42 . 0.0000000000) (91 . 0) (10 987.9188413617 35.4966999996) (40 . 0.0000000000) (41 . 0.0000000000) (42 . 0.0000000000) (91 . 0) (10 987.9028130501 24.3384639426) (40 . 0.0000000000) (41 . 0.0000000000) (42 . 0.0000000000) (91 . 0) (10 986.1109497692 18.7758203153) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (370 . -3) (100 . "AcDbPolyline") (90 . 8) (70 . 1) (43 . 0.0000000000) (38 . 0.0000000000) (39 . 0.0000000000) (10 982.2320082673 36.8650963037) (40 . 0.0000000000) (41 . 0.0000000000) (42 . -0.1594650997) (91 . 0) (10 985.7971605573 38.2950135099) (40 . 0.0000000000) (41 . 0.0000000000) (42 . 0.0000000000) (91 . 0) (10 985.7971605573 37.0168757213) (40 . 0.0000000000) (41 . 0.0000000000) (42 . 0.0000000000) (91 . 0) (10 986.7478831265 37.0168757213) (40 . 0.0000000000) (41 . 0.0000000000) (42 . 0.0000000000) (91 . 0) (10 986.7478831265 38.2837089403) (40 . 0.0000000000) (41 . 0.0000000000) (42 . -0.1569326025) (91 . 0) (10 990.2320082673 36.8095064766) (40 . 0.0000000000) (41 . 0.0000000000) (42 . 0.0000000000) (91 . 0) (10 990.2320082673 35.4966999996) (40 . 0.0000000000) (41 . 0.0000000000) (42 . 0.0000000000) (91 . 0) (10 982.2320082673 35.4966999996) (40 . 0.0000000000) (41 . 0.0000000000) (42 . 0.0000000000) (91 . 0) (210 0.0000000000 0.0000000000 1.0000000000))
((0 . "LWPOLYLINE") (100 . "AcDbEntity") (67 . 0) (8 . "A-Window") (62 . 3) (6 . "Continuous") (100 . "AcDbPolyline") (90 . 44) (70 . 1) (43 . 0.0000000000) (38 . 0.0000000000) (39 . 0.0000000000) (10 -975.6357416372 70.2966877930) (40 . 0.0000000000) (41 . 0.0000000000) (42 . 0.0000000000) (91 . 0) (10 -975.6357416372 70.0967122071) (40 . 0.0000000000) (41 . 0.0000000000) (42 . 0.4142225008) (91 . 0) (10 -975.2357416374 69.6967000001) (40 . 0.0000000000) (41 . 0.0000000000) (42 . 0.0000000000) (91 . 0) (10 -975.0357416373 69.6967000001) (40 . 0.0000000000) (41 . 0.0000000000) (42 . -0.4142135624) (91 . 0) (10 -974.4357416373 69.0967000001) (40 . 0.0000000000) (41 . 0.0000000000) (42 . 0.0000000000) (91 . 0) (10 -974.4357416373 68.8967000001) (40 . 0.0000000000) (41 . 0.0000000000) (42 . -0.2513806714) (91 . 0) (10 -974.7040791583 68.3967000001) (40 . 0.0000000000) (41 . 0.0000000000) (42 . 0.0000000000) (91 . 0) (10 -976.4359158620 68.3967000001) (40 . 0.0000000000) (41 . 0.0000000000) (42 . 0.4142135624) (91 . 0) (10 -976.9359158620 67.8967000001) (40 . 0.0000000000) (41 . 0.0000000000) (42 . 0.0000000000) (91 . 0) (10 -976.9359158620 63.2967000001) (40 . 0.0000000000) (41 . 0.0000000000) (42 . 0.4142135624) (91 . 0) (10 -976.4359158620 62.7967000001) (40 . 0.0000000000) (41 . 0.0000000000) (42 . 0.0000000000) (91 . 0) (10 -976.2257119059 62.7967000001) (40 . 0.0000000000) (41 . 0.0000000000) (42 . 0.0000000000) (91 . 0) (10 -976.0810270105 63.1989988507) (40 . 0.0000000000) (41 . 0.0000000000) (42 . 0.0000000000) (91 . 0) (10 -975.7237895975 63.1989988507) (40 . 0.0000000000) (41 . 0.0000000000) (42 . 0.0000000000) (91 . 0) (10 -975.5840452393 62.7967000001) (40 . 0.0000000000) (41 . 0.0000000000) (42 . 0.0000000000) (91 . 0) (10 -974.9423785726 62.7967000001) (40 . 0.0000000000) (41 . 0.0000000000) (42 . 0.0000000000) (91 . 0) (10 -974.7976936772 63.1989988507) (40 . 0.0000000000) (41 . 0.0000000000) (42 . 0.0000000000) (91 . 0) (10 -974.4404562642 63.1989988507) (40 . 0.0000000000) (41 . 0.0000000000) (42 . 0.0000000000) (91 . 0) (10 -974.3007119059 62.7967000001) (40 . 0.0000000000) (41 . 0.0000000000) (42 . 0.0000000000) (91 . 0) (10 -973.6590452393 62.7967000001) (40 . 0.0000000000) (41 . 0.0000000000) (42 . 0.0000000000) (91 . 0) (10 -973.5143603438 63.1989988507) (40 . 0.0000000000) (41 . 0.0000000000) (42 . 0.0000000000) (91 . 0) (10 -973.1571229309 63.1989988507) (40 . 0.0000000000) (41 . 0.0000000000) (42 . 0.0000000000) (91 . 0) (10 -973.0173785726 62.7967000001) (40 . 0.0000000000) (41 . 0.0000000000) (42 . 0.0000000000) (91 . 0) (10 -972.3757119059 62.7967000001) (40 . 0.0000000000) (41 . 0.0000000000) (42 . 0.0000000000) (91 . 0) (10 -972.2310270105 63.1989988507) (40 . 0.0000000000) (41 . 0.0000000000) (42 . 0.0000000000) (91 . 0) (10 -971.8737895975 63.1989988507) (40 . 0.0000000000) (41 . 0.0000000000) (42 . 0.0000000000) (91 . 0) (10 -971.7340452393 62.7967000001) (40 . 0.0000000000) (41 . 0.0000000000) (42 . 0.0000000000) (91 . 0) (10 -971.0923785726 62.7967000001) (40 . 0.0000000000) (41 . 0.0000000000) (42 . 0.0000000000) (91 . 0) (10 -970.9476936772 63.1989988507) (40 . 0.0000000000) (41 . 0.0000000000) (42 . 0.0000000000) (91 . 0) (10 -970.5904562642 63.1989988507) (40 . 0.0000000000) (41 . 0.0000000000) (42 . 0.0000000000) (91 . 0) (10 -970.4507119059 62.7967000001) (40 . 0.0000000000) (41 . 0.0000000000) (42 . 0.0000000000) (91 . 0) (10 -970.2359158620 62.7967000001) (40 . 0.0000000000) (41 . 0.0000000000) (42 . 0.4142135624) (91 . 0) (10 -969.7359158620 63.2967000001) (40 . 0.0000000000) (41 . 0.0000000000) (42 . 0.0000000000) (91 . 0) (10 -969.7359158620 67.8967000001) (40 . 0.0000000000) (41 . 0.0000000000) (42 . 0.4142135624) (91 . 0) (10 -970.2359158620 68.3967000001) (40 . 0.0000000000) (41 . 0.0000000000) (42 . 0.0000000000) (91 . 0) (10 -971.9674041164 68.3967000001) (40 . 0.0000000000) (41 . 0.0000000000) (42 . -0.2513806714) (91 . 0) (10 -972.2357416374 68.8967000001) (40 . 0.0000000000) (41 . 0.0000000000) (42 . 0.0000000000) (91 . 0) (10 -972.2357416374 69.0967000001) (40 . 0.0000000000) (41 . 0.0000000000) (42 . -0.4142135624) (91 . 0) (10 -971.6357416373 69.6967000001) (40 . 0.0000000000) (41 . 0.0000000000) (42 . 0.0000000000) (91 . 0) (10 -971.4357416373 69.6967000001) (40 . 0.0000000000) (41 . 0.0000000000) (42 . 0.4142135624) (91 . 0) (10 -971.0357416373 70.0967000001) (40 . 0.0000000000) (41 . 0.0000000000) (42 . 0.0000000000) (91 . 0) (10 -971.0357416373 70.2967000001) (40 . 0.0000000000) (41 . 0.0000000000) (42 . 0.4142135624) (91 . 0) (10 -971.4357416373 70.6967000001) (40 . 0.0000000000) (41 . 0.0000000000) (42 . 0.0000000000) (91 . 0) (10 -975.2357416374 70.6967000001) (40 . 0.0000000000) (41 . 0.0000000000) (42 . 0.4142225008) (91 . 0) (210 0.0000000000 0.0000000000 -1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 -971.1809158620 67.3467000001) (40 . 0.0000000000) (41 . 0.0000000000) (42 . 0.0000000000) (91 . 0) (10 -971.1809158620 64.2467000001) (40 . 0.0000000000) (41 . 0.0000000000) (42 . 0.0000000000) (91 . 0) (10 -972.6809158620 64.2467000001) (40 . 0.0000000000) (41 . 0.0000000000) (42 . 0.0000000000) (91 . 0) (10 -972.6809158620 67.3467000001) (40 . 0.0000000000) (41 . 0.0000000000) (42 . 0.0000000000) (91 . 0) (210 0.0000000000 0.0000000000 -1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 -974.0309158620 67.3467000001) (40 . 0.0000000000) (41 . 0.0000000000) (42 . 0.0000000000) (91 . 0) (10 -974.0309158620 64.2467000001) (40 . 0.0000000000) (41 . 0.0000000000) (42 . 0.0000000000) (91 . 0) (10 -975.5309158620 64.2467000001) (40 . 0.0000000000) (41 . 0.0000000000) (42 . 0.0000000000) (91 . 0) (10 -975.5309158620 67.3467000001) (40 . 0.0000000000) (41 . 0.0000000000) (42 . 0.0000000000) (91 . 0) (210 0.0000000000 0.0000000000 -1.0000000000))
((0 . "LINE") (100 . "AcDbEntity") (67 . 0) (8 . "A-Window") (62 . 151) (6 . "Continuous") (100 . "AcDbLine") (10 967.1323432520 62.3966999996 0.0000000000) (11 967.1323432520 67.1967000011 0.0000000000) (210 0.0000000000 0.0000000000 1.0000000000))
((0 . "ARC") (100 . "AcDbEntity") (67 . 0) (8 . "A-Window") (62 . 151) (6 . "Continuous") (100 . "AcDbCircle") (10 1042.8123962019 38.2074976685 0.0000000000) (40 . 10.6781898097) (210 0.0000000000 0.0000000000 1.0000000000) (100 . "AcDbArc") (50 . 2.7687983156) (51 . -3.1031124361))
((0 . "LWPOLYLINE") (100 . "AcDbEntity") (67 . 0) (8 . "A-Window") (62 . 3) (6 . "Continuous") (100 . "AcDbPolyline") (90 . 44) (70 . 1) (43 . 0.0000000000) (38 . 0.0000000000) (39 . 0.0000000000) (10 974.9530983957 34.5713089269) (40 . 0.0000000000) (41 . 0.0000000000) (42 . 0.0000000000) (91 . 0) (10 974.9530983957 34.7712845128) (40 . 0.0000000000) (41 . 0.0000000000) (42 . 0.4142225008) (91 . 0) (10 974.5530983959 35.1712967198) (40 . 0.0000000000) (41 . 0.0000000000) (42 . 0.0000000000) (91 . 0) (10 974.3530983959 35.1712967198) (40 . 0.0000000000) (41 . 0.0000000000) (42 . -0.4142135624) (91 . 0) (10 973.7530983959 35.7712967198) (40 . 0.0000000000) (41 . 0.0000000000) (42 . 0.0000000000) (91 . 0) (10 973.7530983959 35.9712967198) (40 . 0.0000000000) (41 . 0.0000000000) (42 . -0.2513806714) (91 . 0) (10 974.0214359169 36.4712967198) (40 . 0.0000000000) (41 . 0.0000000000) (42 . 0.0000000000) (91 . 0) (10 975.7532726205 36.4712967198) (40 . 0.0000000000) (41 . 0.0000000000) (42 . 0.4142135624) (91 . 0) (10 976.2532726205 36.9712967198) (40 . 0.0000000000) (41 . 0.0000000000) (42 . 0.0000000000) (91 . 0) (10 976.2532726205 41.5712967198) (40 . 0.0000000000) (41 . 0.0000000000) (42 . 0.4142135624) (91 . 0) (10 975.7532726205 42.0712967198) (40 . 0.0000000000) (41 . 0.0000000000) (42 . 0.0000000000) (91 . 0) (10 975.5430686645 42.0712967198) (40 . 0.0000000000) (41 . 0.0000000000) (42 . 0.0000000000) (91 . 0) (10 975.3983837691 41.6689978692) (40 . 0.0000000000) (41 . 0.0000000000) (42 . 0.0000000000) (91 . 0) (10 975.0411463561 41.6689978692) (40 . 0.0000000000) (41 . 0.0000000000) (42 . 0.0000000000) (91 . 0) (10 974.9014019978 42.0712967198) (40 . 0.0000000000) (41 . 0.0000000000) (42 . 0.0000000000) (91 . 0) (10 974.2597353311 42.0712967198) (40 . 0.0000000000) (41 . 0.0000000000) (42 . 0.0000000000) (91 . 0) (10 974.1150504357 41.6689978692) (40 . 0.0000000000) (41 . 0.0000000000) (42 . 0.0000000000) (91 . 0) (10 973.7578130227 41.6689978692) (40 . 0.0000000000) (41 . 0.0000000000) (42 . 0.0000000000) (91 . 0) (10 973.6180686645 42.0712967198) (40 . 0.0000000000) (41 . 0.0000000000) (42 . 0.0000000000) (91 . 0) (10 972.9764019978 42.0712967198) (40 . 0.0000000000) (41 . 0.0000000000) (42 . 0.0000000000) (91 . 0) (10 972.8317171024 41.6689978692) (40 . 0.0000000000) (41 . 0.0000000000) (42 . 0.0000000000) (91 . 0) (10 972.4744796894 41.6689978692) (40 . 0.0000000000) (41 . 0.0000000000) (42 . 0.0000000000) (91 . 0) (10 972.3347353311 42.0712967198) (40 . 0.0000000000) (41 . 0.0000000000) (42 . 0.0000000000) (91 . 0) (10 971.6930686645 42.0712967198) (40 . 0.0000000000) (41 . 0.0000000000) (42 . 0.0000000000) (91 . 0) (10 971.5483837691 41.6689978692) (40 . 0.0000000000) (41 . 0.0000000000) (42 . 0.0000000000) (91 . 0) (10 971.1911463561 41.6689978692) (40 . 0.0000000000) (41 . 0.0000000000) (42 . 0.0000000000) (91 . 0) (10 971.0514019978 42.0712967198) (40 . 0.0000000000) (41 . 0.0000000000) (42 . 0.0000000000) (91 . 0) (10 970.4097353311 42.0712967198) (40 . 0.0000000000) (41 . 0.0000000000) (42 . 0.0000000000) (91 . 0) (10 970.2650504357 41.6689978692) (40 . 0.0000000000) (41 . 0.0000000000) (42 . 0.0000000000) (91 . 0) (10 969.9078130227 41.6689978692) (40 . 0.0000000000) (41 . 0.0000000000) (42 . 0.0000000000) (91 . 0) (10 969.7680686645 42.0712967198) (40 . 0.0000000000) (41 . 0.0000000000) (42 . 0.0000000000) (91 . 0) (10 969.5532726205 42.0712967198) (40 . 0.0000000000) (41 . 0.0000000000) (42 . 0.4142135624) (91 . 0) (10 969.0532726205 41.5712967198) (40 . 0.0000000000) (41 . 0.0000000000) (42 . 0.0000000000) (91 . 0) (10 969.0532726205 36.9712967198) (40 . 0.0000000000) (41 . 0.0000000000) (42 . 0.4142135624) (91 . 0) (10 969.5532726205 36.4712967198) (40 . 0.0000000000) (41 . 0.0000000000) (42 . 0.0000000000) (91 . 0) (10 971.2847608749 36.4712967198) (40 . 0.0000000000) (41 . 0.0000000000) (42 . -0.2513806714) (91 . 0) (10 971.5530983959 35.9712967198) (40 . 0.0000000000) (41 . 0.0000000000) (42 . 0.0000000000) (91 . 0) (10 971.5530983959 35.7712967198) (40 . 0.0000000000) (41 . 0.0000000000) (42 . -0.4142135624) (91 . 0) (10 970.9530983959 35.1712967198) (40 . 0.0000000000) (41 . 0.0000000000) (42 . 0.0000000000) (91 . 0) (10 970.7530983959 35.1712967198) (40 . 0.0000000000) (41 . 0.0000000000) (42 . 0.4142135624) (91 . 0) (10 970.3530983959 34.7712967198) (40 . 0.0000000000) (41 . 0.0000000000) (42 . 0.0000000000) (91 . 0) (10 970.3530983959 34.5712967198) (40 . 0.0000000000) (41 . 0.0000000000) (42 . 0.4142135624) (91 . 0) (10 970.7530983959 34.1712967198) (40 . 0.0000000000) (41 . 0.0000000000) (42 . 0.0000000000) (91 . 0) (10 974.5530983959 34.1712967198) (40 . 0.0000000000) (41 . 0.0000000000) (42 . 0.4142225008) (91 . 0) (210 0.0000000000 0.0000000000 1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 970.4982726205 37.5212967198) (40 . 0.0000000000) (41 . 0.0000000000) (42 . 0.0000000000) (91 . 0) (10 970.4982726205 40.6212967198) (40 . 0.0000000000) (41 . 0.0000000000) (42 . 0.0000000000) (91 . 0) (10 971.9982726205 40.6212967198) (40 . 0.0000000000) (41 . 0.0000000000) (42 . 0.0000000000) (91 . 0) (10 971.9982726205 37.5212967198) (40 . 0.0000000000) (41 . 0.0000000000) (42 . 0.0000000000) (91 . 0) (210 0.0000000000 0.0000000000 1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 973.3482726205 37.5212967198) (40 . 0.0000000000) (41 . 0.0000000000) (42 . 0.0000000000) (91 . 0) (10 973.3482726205 40.6212967198) (40 . 0.0000000000) (41 . 0.0000000000) (42 . 0.0000000000) (91 . 0) (10 974.8482726205 40.6212967198) (40 . 0.0000000000) (41 . 0.0000000000) (42 . 0.0000000000) (91 . 0) (10 974.8482726205 37.5212967198) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 967.1323432520 42.6610141281 0.0000000000) (11 967.1323432520 37.8610141265 0.0000000000) (210 0.0000000000 0.0000000000 1.0000000000))
((0 . "LWPOLYLINE") (100 . "AcDbEntity") (67 . 0) (8 . "A-Window") (62 . 151) (6 . "Continuous") (100 . "AcDbPolyline") (90 . 8) (70 . 1) (43 . 0.0000000000) (38 . 0.0000000000) (39 . 0.0000000000) (10 -29.8578888394 -90.5967000000) (40 . 0.0000000000) (41 . 0.0000000000) (42 . -0.4142135624) (91 . 0) (10 -30.3578888394 -90.0967000000) (40 . 0.0000000000) (41 . 0.0000000000) (42 . 0.0000000000) (91 . 0) (10 -30.3578888394 30.4967000000) (40 . 0.0000000000) (41 . 0.0000000000) (42 . -0.4142135624) (91 . 0) (10 -29.8578888394 30.9967000000) (40 . 0.0000000000) (41 . 0.0000000000) (42 . 0.0000000000) (91 . 0) (10 29.1421111606 30.9967000000) (40 . 0.0000000000) (41 . 0.0000000000) (42 . -0.4142135624) (91 . 0) (10 29.6421111606 30.4967000000) (40 . 0.0000000000) (41 . 0.0000000000) (42 . 0.0000000000) (91 . 0) (10 29.6421111606 -90.0967000000) (40 . 0.0000000000) (41 . 0.0000000000) (42 . -0.4142135624) (91 . 0) (10 29.1421111606 -90.5967000000) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 87) (70 . 1) (43 . 0.0000000000) (38 . 0.0000000000) (39 . 0.0000000000) (10 -29.7578888394 34.6967000000) (40 . 0.0000000000) (41 . 0.0000000000) (42 . 0.0000000000) (91 . 0) (10 -29.7578888394 34.4967000000) (40 . 0.0000000000) (41 . 0.0000000000) (42 . 0.4142135624) (91 . 0) (10 -29.2578888394 33.9967000000) (40 . 0.0000000000) (41 . 0.0000000000) (42 . 0.0000000000) (91 . 0) (10 -25.4578888394 33.9967000000) (40 . 0.0000000000) (41 . 0.0000000000) (42 . 0.4142135624) (91 . 0) (10 -24.9578888394 34.4967000000) (40 . 0.0000000000) (41 . 0.0000000000) (42 . 0.0000000000) (91 . 0) (10 -24.9578888394 34.6967000000) (40 . 0.0000000000) (41 . 0.0000000000) (42 . 0.4142135624) (91 . 0) (10 -25.4578888394 35.1967000000) (40 . 0.0000000000) (41 . 0.0000000000) (42 . 0.0000000000) (91 . 0) (10 -25.6578888394 35.1967000000) (40 . 0.0000000000) (41 . 0.0000000000) (42 . -0.4142135624) (91 . 0) (10 -26.1578888394 35.6967000000) (40 . 0.0000000000) (41 . 0.0000000000) (42 . 0.0000000000) (91 . 0) (10 -26.1578888394 35.8967000000) (40 . 0.0000000000) (41 . 0.0000000000) (42 . -0.4142135624) (91 . 0) (10 -25.6578888394 36.3967000000) (40 . 0.0000000000) (41 . 0.0000000000) (42 . 0.0000000000) (91 . 0) (10 -24.2578888394 36.3967000000) (40 . 0.0000000000) (41 . 0.0000000000) (42 . -0.4142135624) (91 . 0) (10 -23.7578888394 35.8967000000) (40 . 0.0000000000) (41 . 0.0000000000) (42 . 0.0000000000) (91 . 0) (10 -23.7578888394 34.4967000000) (40 . 0.0000000000) (41 . 0.0000000000) (42 . 0.4142135624) (91 . 0) (10 -23.2578888394 33.9967000000) (40 . 0.0000000000) (41 . 0.0000000000) (42 . 0.0000000000) (91 . 0) (10 -9.3578888394 33.9967000000) (40 . 0.0000000000) (41 . 0.0000000000) (42 . 0.4142135624) (91 . 0) (10 -8.8578888394 34.4967000000) (40 . 0.0000000000) (41 . 0.0000000000) (42 . 0.0000000000) (91 . 0) (10 -8.8578888394 55.8967000000) (40 . 0.0000000000) (41 . 0.0000000000) (42 . -0.4142135624) (91 . 0) (10 -8.3578888394 56.3967000000) (40 . 0.0000000000) (41 . 0.0000000000) (42 . 0.0000000000) (91 . 0) (10 -6.0578936442 56.3967000000) (40 . 0.0000000000) (41 . 0.0000000000) (42 . 0.0000000000) (91 . 0) (10 -5.0809431613 54.4427990332) (40 . 0.0000000000) (41 . 0.0000000000) (42 . -0.4142135643) (91 . 0) (10 -5.1703858816 54.1744708754) (40 . 0.0000000000) (41 . 0.0000000000) (42 . 0.0000000000) (91 . 0) (10 -5.3492713179 54.0850281587) (40 . 0.0000000000) (41 . 0.0000000000) (42 . 0.4142135643) (91 . 0) (10 -5.4387140381 53.8167000008) (40 . 0.0000000000) (41 . 0.0000000000) (42 . 0.0000000000) (91 . 0) (10 -4.8339926779 52.6072572806) (40 . 0.0000000000) (41 . 0.0000000000) (42 . 0.2840790438) (91 . 0) (10 -4.6551072397 52.4966999997) (40 . 0.0000000000) (41 . 0.0000000000) (42 . 0.0000000000) (91 . 0) (10 -1.0235742645 52.4966999997) (40 . 0.0000000000) (41 . 0.0000000000) (42 . -0.1989123674) (91 . 0) (10 -0.8821529082 52.4381213559) (40 . 0.0000000000) (41 . 0.0000000000) (42 . 0.0000000000) (91 . 0) (10 -0.4993101957 52.0552786434) (40 . 0.0000000000) (41 . 0.0000000000) (42 . 0.1989123674) (91 . 0) (10 -0.3578888395 51.9966999997) (40 . 0.0000000000) (41 . 0.0000000000) (42 . 0.1989123674) (91 . 0) (10 -0.2164674833 52.0552786434) (40 . 0.0000000000) (41 . 0.0000000000) (42 . 0.0000000000) (91 . 0) (10 0.1663752292 52.4381213559) (40 . 0.0000000000) (41 . 0.0000000000) (42 . -0.1989123674) (91 . 0) (10 0.3077965854 52.4966999997) (40 . 0.0000000000) (41 . 0.0000000000) (42 . 0.0000000000) (91 . 0) (10 3.9393295607 52.4966999997) (40 . 0.0000000000) (41 . 0.0000000000) (42 . 0.2840790438) (91 . 0) (10 4.1182149988 52.6072572805) (40 . 0.0000000000) (41 . 0.0000000000) (42 . 0.0000000000) (91 . 0) (10 4.7229363593 53.8167000007) (40 . 0.0000000000) (41 . 0.0000000000) (42 . 0.4142135642) (91 . 0) (10 4.6334936391 54.0850281586) (40 . 0.0000000000) (41 . 0.0000000000) (42 . 0.0000000000) (91 . 0) (10 4.4546082026 54.1744708755) (40 . 0.0000000000) (41 . 0.0000000000) (42 . -0.4142135641) (91 . 0) (10 4.3651654824 54.4427990333) (40 . 0.0000000000) (41 . 0.0000000000) (42 . 0.0000000000) (91 . 0) (10 5.3421159653 56.3967000000) (40 . 0.0000000000) (41 . 0.0000000000) (42 . 0.0000000000) (91 . 0) (10 7.6421111606 56.3967000000) (40 . 0.0000000000) (41 . 0.0000000000) (42 . -0.4142135624) (91 . 0) (10 8.1421111606 55.8967000000) (40 . 0.0000000000) (41 . 0.0000000000) (42 . 0.0000000000) (91 . 0) (10 8.1421111606 34.4967000000) (40 . 0.0000000000) (41 . 0.0000000000) (42 . 0.4142135624) (91 . 0) (10 8.6421111606 33.9967000000) (40 . 0.0000000000) (41 . 0.0000000000) (42 . 0.0000000000) (91 . 0) (10 22.5421111606 33.9967000000) (40 . 0.0000000000) (41 . 0.0000000000) (42 . 0.4142135624) (91 . 0) (10 23.0421111606 34.4967000000) (40 . 0.0000000000) (41 . 0.0000000000) (42 . 0.0000000000) (91 . 0) (10 23.0421111606 35.8967000000) (40 . 0.0000000000) (41 . 0.0000000000) (42 . -0.4142135624) (91 . 0) (10 23.5421111606 36.3967000000) (40 . 0.0000000000) (41 . 0.0000000000) (42 . 0.0000000000) (91 . 0) (10 24.9421111606 36.3967000000) (40 . 0.0000000000) (41 . 0.0000000000) (42 . -0.4142135624) (91 . 0) (10 25.4421111606 35.8967000000) (40 . 0.0000000000) (41 . 0.0000000000) (42 . 0.0000000000) (91 . 0) (10 25.4421111606 35.6967000000) (40 . 0.0000000000) (41 . 0.0000000000) (42 . -0.4142135624) (91 . 0) (10 24.9421111606 35.1967000000) (40 . 0.0000000000) (41 . 0.0000000000) (42 . 0.0000000000) (91 . 0) (10 24.7421111606 35.1967000000) (40 . 0.0000000000) (41 . 0.0000000000) (42 . 0.4142135624) (91 . 0) (10 24.2421111606 34.6967000000) (40 . 0.0000000000) (41 . 0.0000000000) (42 . 0.0000000000) (91 . 0) (10 24.2421111606 34.4967000000) (40 . 0.0000000000) (41 . 0.0000000000) (42 . 0.4142135624) (91 . 0) (10 24.7421111606 33.9967000000) (40 . 0.0000000000) (41 . 0.0000000000) (42 . 0.0000000000) (91 . 0) (10 28.5421111606 33.9967000000) (40 . 0.0000000000) (41 . 0.0000000000) (42 . 0.4142135624) (91 . 0) (10 29.0421111606 34.4967000000) (40 . 0.0000000000) (41 . 0.0000000000) (42 . 0.0000000000) (91 . 0) (10 29.0421111606 34.6967000000) (40 . 0.0000000000) (41 . 0.0000000000) (42 . 0.4142135624) (91 . 0) (10 28.5421111606 35.1967000000) (40 . 0.0000000000) (41 . 0.0000000000) (42 . 0.0000000000) (91 . 0) (10 28.3421111606 35.1967000000) (40 . 0.0000000000) (41 . 0.0000000000) (42 . -0.4142135624) (91 . 0) (10 27.8421111606 35.6967000000) (40 . 0.0000000000) (41 . 0.0000000000) (42 . 0.0000000000) (91 . 0) (10 27.8421111606 35.8967000000) (40 . 0.0000000000) (41 . 0.0000000000) (42 . -0.4142135624) (91 . 0) (10 28.3421111606 36.3967000000) (40 . 0.0000000000) (41 . 0.0000000000) (42 . 0.0000000000) (91 . 0) (10 30.4421111606 36.3967000000) (40 . 0.0000000000) (41 . 0.0000000000) (42 . 0.4142135624) (91 . 0) (10 30.9421111606 36.8967000000) (40 . 0.0000000000) (41 . 0.0000000000) (42 . 0.0000000000) (91 . 0) (10 30.9421111606 37.8967000000) (40 . 0.0000000000) (41 . 0.0000000000) (42 . -0.4142135624) (91 . 0) (10 31.4421111606 38.3967000000) (40 . 0.0000000000) (41 . 0.0000000000) (42 . 0.0000000000) (91 . 0) (10 31.6421111606 38.3967000000) (40 . 0.0000000000) (41 . 0.0000000000) (42 . -0.4142135624) (91 . 0) (10 32.1421111606 37.8967000000) (40 . 0.0000000000) (41 . 0.0000000000) (42 . 0.0000000000) (91 . 0) (10 32.1421111606 33.9967000000) (40 . 0.0000000000) (41 . 0.0000000000) (42 . 0.0000000000) (91 . 0) (10 32.1421111606 -93.0967000000) (40 . 0.0000000000) (41 . 0.0000000000) (42 . -0.4142135624) (91 . 0) (10 31.6421111606 -93.5967000000) (40 . 0.0000000000) (41 . 0.0000000000) (42 . 0.0000000000) (91 . 0) (10 -32.3578888394 -93.5967000000) (40 . 0.0000000000) (41 . 0.0000000000) (42 . -0.4142135624) (91 . 0) (10 -32.8578888394 -93.0967000000) (40 . 0.0000000000) (41 . 0.0000000000) (42 . 0.0000000000) (91 . 0) (10 -32.8578888394 33.9967000000) (40 . 0.0000000000) (41 . 0.0000000000) (42 . 0.0000000000) (91 . 0) (10 -32.8578888394 37.8967000000) (40 . 0.0000000000) (41 . 0.0000000000) (42 . -0.4142135624) (91 . 0) (10 -32.3578888394 38.3967000000) (40 . 0.0000000000) (41 . 0.0000000000) (42 . 0.0000000000) (91 . 0) (10 -32.1578888394 38.3967000000) (40 . 0.0000000000) (41 . 0.0000000000) (42 . -0.4142135624) (91 . 0) (10 -31.6578888394 37.8967000000) (40 . 0.0000000000) (41 . 0.0000000000) (42 . 0.0000000000) (91 . 0) (10 -31.6578888394 36.8967000000) (40 . 0.0000000000) (41 . 0.0000000000) (42 . 0.4142135624) (91 . 0) (10 -31.1578888394 36.3967000000) (40 . 0.0000000000) (41 . 0.0000000000) (42 . 0.0000000000) (91 . 0) (10 -29.0578888394 36.3967000000) (40 . 0.0000000000) (41 . 0.0000000000) (42 . -0.4142135624) (91 . 0) (10 -28.5578888394 35.8967000000) (40 . 0.0000000000) (41 . 0.0000000000) (42 . 0.0000000000) (91 . 0) (10 -28.5578888394 35.6967000000) (40 . 0.0000000000) (41 . 0.0000000000) (42 . -0.4142135624) (91 . 0) (10 -29.0578888394 35.1967000000) (40 . 0.0000000000) (41 . 0.0000000000) (42 . 0.0000000000) (91 . 0) (10 -29.2578888394 35.1967000000) (40 . 0.0000000000) (41 . 0.0000000000) (42 . 0.4142135624) (91 . 0) (210 0.0000000000 0.0000000000 1.0000000000))
((0 . "LWPOLYLINE") (100 . "AcDbEntity") (67 . 0) (8 . "A-Window") (62 . 151) (6 . "Continuous") (100 . "AcDbPolyline") (90 . 17) (70 . 1) (43 . 0.0000000000) (38 . 0.0000000000) (39 . 0.0000000000) (10 -0.3578888395 47.4966999996) (40 . 0.0000000000) (41 . 0.0000000000) (42 . 0.0000000000) (91 . 0) (10 2.8235760300 47.4966999996) (40 . 0.0000000000) (41 . 0.0000000000) (42 . 0.2914734196) (91 . 0) (10 3.2767299235 47.7853908688) (40 . 0.0000000000) (41 . 0.0000000000) (42 . 0.0000000000) (91 . 0) (10 4.1732615427 49.7080091306) (40 . 0.0000000000) (41 . 0.0000000000) (42 . -0.2914734196) (91 . 0) (10 4.6264154362 49.9966999997) (40 . 0.0000000000) (41 . 0.0000000000) (42 . 0.0000000000) (91 . 0) (10 5.6421111605 49.9966999997) (40 . 0.0000000000) (41 . 0.0000000000) (42 . -0.4142135624) (91 . 0) (10 6.1421111605 49.4966999997) (40 . 0.0000000000) (41 . 0.0000000000) (42 . 0.0000000000) (91 . 0) (10 6.1421111605 34.4967000000) (40 . 0.0000000000) (41 . 0.0000000000) (42 . -0.4142135624) (91 . 0) (10 5.6421111605 33.9967000000) (40 . 0.0000000000) (41 . 0.0000000000) (42 . 0.0000000000) (91 . 0) (10 -6.3578888395 33.9967000000) (40 . 0.0000000000) (41 . 0.0000000000) (42 . -0.4142135624) (91 . 0) (10 -6.8578888395 34.4967000000) (40 . 0.0000000000) (41 . 0.0000000000) (42 . 0.0000000000) (91 . 0) (10 -6.8578888395 49.4966999997) (40 . 0.0000000000) (41 . 0.0000000000) (42 . -0.4142135624) (91 . 0) (10 -6.3578888395 49.9966999997) (40 . 0.0000000000) (41 . 0.0000000000) (42 . 0.0000000000) (91 . 0) (10 -5.3421931154 49.9966999997) (40 . 0.0000000000) (41 . 0.0000000000) (42 . -0.2914734196) (91 . 0) (10 -4.8890392219 49.7080091306) (40 . 0.0000000000) (41 . 0.0000000000) (42 . 0.0000000000) (91 . 0) (10 -3.9925076027 47.7853908688) (40 . 0.0000000000) (41 . 0.0000000000) (42 . 0.2914734196) (91 . 0) (10 -3.5393537092 47.4966999996) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 12) (70 . 1) (43 . 0.0000000000) (38 . 0.0000000000) (39 . 0.0000000000) (10 -6.1467510526 61.6983038651) (40 . 0.0000000000) (41 . 0.0000000000) (42 . -0.2849552787) (91 . 0) (10 -6.2578888319 61.8774783771) (40 . 0.0000000000) (41 . 0.0000000000) (42 . 0.0000000000) (91 . 0) (10 -6.2578888319 61.7734539607) (40 . 0.0000000000) (41 . 0.0000000000) (42 . -0.5564744028) (91 . 0) (10 -5.5357332802 62.2213902406) (40 . 0.0000000000) (41 . 0.0000000000) (42 . 0.0000000000) (91 . 0) (10 -0.5800443918 62.7635991465) (40 . 0.0000000000) (41 . 0.0000000000) (42 . 0.2343570514) (91 . 0) (10 -0.1357332887 62.7635991463) (40 . 0.0000000000) (41 . 0.0000000000) (42 . 0.0000000000) (91 . 0) (10 4.8199556166 62.2213902421) (40 . 0.0000000000) (41 . 0.0000000000) (42 . -0.5564744024) (91 . 0) (10 5.5421111679 61.7734539620) (40 . 0.0000000000) (41 . 0.0000000000) (42 . 0.0000000000) (91 . 0) (10 5.5421111679 61.8774783772) (40 . 0.0000000000) (41 . 0.0000000000) (42 . -0.2849552790) (91 . 0) (10 5.4309733884 61.6983038651) (40 . 0.0000000000) (41 . 0.0000000000) (42 . 0.0000000000) (91 . 0) (10 -0.1357332882 58.9374763869) (40 . 0.0000000000) (41 . 0.0000000000) (42 . -0.2343570514) (91 . 0) (10 -0.5800443913 58.9374763871) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 65) (70 . 0) (43 . 0.0000000000) (38 . 0.0000000000) (39 . 0.0000000000) (10 -4.8578888320 67.1313221971) (40 . 0.0000000000) (41 . 0.0000000000) (42 . 0.0000000000) (91 . 0) (10 -4.8578888320 66.5967000000) (40 . 0.0000000000) (41 . 0.0000000000) (42 . -0.4142135624) (91 . 0) (10 -5.0578888322 66.3967000000) (40 . 0.0000000000) (41 . 0.0000000000) (42 . 0.0000000000) (91 . 0) (10 -6.0578888322 66.3967000000) (40 . 0.0000000000) (41 . 0.0000000000) (42 . 0.4142135624) (91 . 0) (10 -6.2578888319 66.1967000000) (40 . 0.0000000000) (41 . 0.0000000000) (42 . 0.0000000000) (91 . 0) (10 -6.2578888319 64.3779464253) (40 . 0.0000000000) (41 . 0.0000000000) (42 . 0.2849552787) (91 . 0) (10 -6.1467510526 64.1987719134) (40 . 0.0000000000) (41 . 0.0000000000) (42 . 0.0000000000) (91 . 0) (10 -0.5800443909 61.4379444351) (40 . 0.0000000000) (41 . 0.0000000000) (42 . 0.2343570514) (91 . 0) (10 -0.1357332879 61.4379444349) (40 . 0.0000000000) (41 . 0.0000000000) (42 . 0.0000000000) (91 . 0) (10 5.4309733884 64.1987719129) (40 . 0.0000000000) (41 . 0.0000000000) (42 . 0.2849552790) (91 . 0) (10 5.5421111679 64.3779464250) (40 . 0.0000000000) (41 . 0.0000000000) (42 . 0.0000000000) (91 . 0) (10 5.5421111679 66.1967000000) (40 . 0.0000000000) (41 . 0.0000000000) (42 . 0.4142135624) (91 . 0) (10 5.3421111677 66.3966999999) (40 . 0.0000000000) (41 . 0.0000000000) (42 . 0.0000000000) (91 . 0) (10 4.3421111677 66.3966999999) (40 . 0.0000000000) (41 . 0.0000000000) (42 . -0.4142135624) (91 . 0) (10 4.1421111680 66.5967000000) (40 . 0.0000000000) (41 . 0.0000000000) (42 . 0.0000000000) (91 . 0) (10 4.1421111680 67.1189032619) (40 . 0.0000000000) (41 . 0.0000000000) (42 . -0.1876437528) (91 . 0) (10 4.1946803399 67.2540481876) (40 . 0.0000000000) (41 . 0.0000000000) (42 . 0.0000000000) (91 . 0) (10 5.1826606833 68.3318449257) (40 . 0.0000000000) (41 . 0.0000000000) (42 . -0.2102297862) (91 . 0) (10 5.3300915111 68.3966999999) (40 . 0.0000000000) (41 . 0.0000000000) (42 . 0.0000000000) (91 . 0) (10 6.9421111678 68.3966999999) (40 . 0.0000000000) (41 . 0.0000000000) (42 . -0.4142135624) (91 . 0) (10 7.1421111680 68.1967000000) (40 . 0.0000000000) (41 . 0.0000000000) (42 . 0.0000000000) (91 . 0) (10 7.1421111680 56.5967000000) (40 . 0.0000000000) (41 . 0.0000000000) (42 . -0.4142135624) (91 . 0) (10 6.9421111678 56.3966999999) (40 . 0.0000000000) (41 . 0.0000000000) (42 . 0.0000000000) (91 . 0) (10 5.9421111678 56.3966999999) (40 . 0.0000000000) (41 . 0.0000000000) (42 . -0.4142135624) (91 . 0) (10 5.7421111681 56.5967000000) (40 . 0.0000000000) (41 . 0.0000000000) (42 . 0.0000000000) (91 . 0) (10 5.7421111681 59.0967000000) (40 . 0.0000000000) (41 . 0.0000000000) (42 . 0.5788431251) (91 . 0) (10 4.9901756553 59.5285894504) (40 . 0.0000000000) (41 . 0.0000000000) (42 . 0.0000000000) (91 . 0) (10 4.4199556161 59.2457868447) (40 . 0.0000000000) (41 . 0.0000000000) (42 . 0.2849552788) (91 . 0) (10 4.1421111680 58.7978505647) (40 . 0.0000000000) (41 . 0.0000000000) (42 . 0.0000000000) (91 . 0) (10 4.1421111680 54.3533563146) (40 . 0.0000000000) (41 . 0.0000000000) (42 . 0.2840790438) (91 . 0) (10 4.2526684489 54.1744708764) (40 . 0.0000000000) (41 . 0.0000000000) (42 . 0.0000000000) (91 . 0) (10 4.4315538869 54.0850281572) (40 . 0.0000000000) (41 . 0.0000000000) (42 . -0.4142135624) (91 . 0) (10 4.5209966062 53.8167000000) (40 . 0.0000000000) (41 . 0.0000000000) (42 . 0.0000000000) (91 . 0) (10 3.9162752462 52.6072572809) (40 . 0.0000000000) (41 . 0.0000000000) (42 . -0.2840790438) (91 . 0) (10 3.7373898082 52.4967000000) (40 . 0.0000000000) (41 . 0.0000000000) (42 . 0.0000000000) (91 . 0) (10 3.0609966062 52.4967000000) (40 . 0.0000000000) (41 . 0.0000000000) (42 . -0.4142135624) (91 . 0) (10 2.8609966060 52.6967000000) (40 . 0.0000000000) (41 . 0.0000000000) (42 . 0.0000000000) (91 . 0) (10 2.8609966060 57.9432778508) (40 . 0.0000000000) (41 . 0.0000000000) (42 . 0.5564744024) (91 . 0) (10 2.1388410547 58.3912141310) (40 . 0.0000000000) (41 . 0.0000000000) (42 . 0.0000000000) (91 . 0) (10 -0.2690266202 57.1970238086) (40 . 0.0000000000) (41 . 0.0000000000) (42 . -0.2343570514) (91 . 0) (10 -0.4467510614 57.1970238087) (40 . 0.0000000000) (41 . 0.0000000000) (42 . 0.0000000000) (91 . 0) (10 -2.8546187183 58.3912141254) (40 . 0.0000000000) (41 . 0.0000000000) (42 . 0.5564744028) (91 . 0) (10 -3.5767742701 57.9432778455) (40 . 0.0000000000) (41 . 0.0000000000) (42 . 0.0000000000) (91 . 0) (10 -3.5767742701 52.6967000000) (40 . 0.0000000000) (41 . 0.0000000000) (42 . -0.4142135624) (91 . 0) (10 -3.7767742703 52.4967000000) (40 . 0.0000000000) (41 . 0.0000000000) (42 . 0.0000000000) (91 . 0) (10 -4.4531674728 52.4967000000) (40 . 0.0000000000) (41 . 0.0000000000) (42 . -0.2840790438) (91 . 0) (10 -4.6320529108 52.6072572809) (40 . 0.0000000000) (41 . 0.0000000000) (42 . 0.0000000000) (91 . 0) (10 -5.2367742702 53.8167000000) (40 . 0.0000000000) (41 . 0.0000000000) (42 . -0.4142135624) (91 . 0) (10 -5.1473315514 54.0850281573) (40 . 0.0000000000) (41 . 0.0000000000) (42 . 0.0000000000) (91 . 0) (10 -4.9684461130 54.1744708764) (40 . 0.0000000000) (41 . 0.0000000000) (42 . 0.2840790438) (91 . 0) (10 -4.8578888320 54.3533563146) (40 . 0.0000000000) (41 . 0.0000000000) (42 . 0.0000000000) (91 . 0) (10 -4.8578888320 58.7978505647) (40 . 0.0000000000) (41 . 0.0000000000) (42 . 0.2849552788) (91 . 0) (10 -5.1357332806 59.2457868447) (40 . 0.0000000000) (41 . 0.0000000000) (42 . 0.0000000000) (91 . 0) (10 -5.7059533194 59.5285894504) (40 . 0.0000000000) (41 . 0.0000000000) (42 . 0.5788431251) (91 . 0) (10 -6.4578888321 59.0967000000) (40 . 0.0000000000) (41 . 0.0000000000) (42 . 0.0000000000) (91 . 0) (10 -6.4578888321 56.5967000000) (40 . 0.0000000000) (41 . 0.0000000000) (42 . -0.4142135624) (91 . 0) (10 -6.6578888323 56.3967000000) (40 . 0.0000000000) (41 . 0.0000000000) (42 . 0.0000000000) (91 . 0) (10 -7.6578888323 56.3967000000) (40 . 0.0000000000) (41 . 0.0000000000) (42 . -0.4142135624) (91 . 0) (10 -7.8578888320 56.5967000000) (40 . 0.0000000000) (41 . 0.0000000000) (42 . 0.0000000000) (91 . 0) (10 -7.8578888320 68.1967000000) (40 . 0.0000000000) (41 . 0.0000000000) (42 . -0.4142135624) (91 . 0) (10 -7.6578888323 68.3967000000) (40 . 0.0000000000) (41 . 0.0000000000) (42 . 0.0000000000) (91 . 0) (10 -6.0454832279 68.3966999999) (40 . 0.0000000000) (41 . 0.0000000000) (42 . -0.2102297862) (91 . 0) (10 -5.8980524000 68.3318449257) (40 . 0.0000000000) (41 . 0.0000000000) (42 . 0.0000000000) (91 . 0) (10 -4.9100720566 67.2540481876) (40 . 0.0000000000) (41 . 0.0000000000) (42 . -0.1876437528) (91 . 0) (10 -4.8575028848 67.1189032619) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 80) (70 . 1) (43 . 0.0000000000) (38 . 0.0000000000) (39 . 0.0000000000) (10 20.9421111602 72.8967000000) (40 . 0.0000000000) (41 . 0.0000000000) (42 . -0.4142135624) (91 . 0) (10 21.4421111602 73.3967000000) (40 . 0.0000000000) (41 . 0.0000000000) (42 . 0.0000000000) (91 . 0) (10 28.0421111602 73.3967000000) (40 . 0.0000000000) (41 . 0.0000000000) (42 . 0.4142135624) (91 . 0) (10 28.5421111602 73.8967000000) (40 . 0.0000000000) (41 . 0.0000000000) (42 . 0.0000000000) (91 . 0) (10 28.5421111602 77.8967000000) (40 . 0.0000000000) (41 . 0.0000000000) (42 . -0.4142135624) (91 . 0) (10 29.0421111602 78.3967000000) (40 . 0.0000000000) (41 . 0.0000000000) (42 . 0.0000000000) (91 . 0) (10 29.3405054536 78.3967000000) (40 . 0.0000000000) (41 . 0.0000000000) (42 . -0.3152987889) (91 . 0) (10 29.8103517640 78.0677100716) (40 . 0.0000000000) (41 . 0.0000000000) (42 . 0.0000000000) (91 . 0) (10 30.4300496843 76.3651040286) (40 . 0.0000000000) (41 . 0.0000000000) (42 . -0.5205670506) (91 . 0) (10 30.2421111602 76.0967000000) (40 . 0.0000000000) (41 . 0.0000000000) (42 . 0.0000000000) (91 . 0) (10 30.0421111602 76.0967000000) (40 . 0.0000000000) (41 . 0.0000000000) (42 . 0.4142135624) (91 . 0) (10 29.7421111602 75.7967000000) (40 . 0.0000000000) (41 . 0.0000000000) (42 . 0.0000000000) (91 . 0) (10 29.7421111602 73.8967000000) (40 . 0.0000000000) (41 . 0.0000000000) (42 . 0.4142135624) (91 . 0) (10 30.2421111602 73.3967000000) (40 . 0.0000000000) (41 . 0.0000000000) (42 . 0.0000000000) (91 . 0) (10 30.4421111602 73.3967000000) (40 . 0.0000000000) (41 . 0.0000000000) (42 . -0.4142135624) (91 . 0) (10 30.9421111602 72.8967000000) (40 . 0.0000000000) (41 . 0.0000000000) (42 . 0.0000000000) (91 . 0) (10 30.9421111602 68.8967000000) (40 . 0.0000000000) (41 . 0.0000000000) (42 . -0.4142135624) (91 . 0) (10 30.4421111602 68.3967000000) (40 . 0.0000000000) (41 . 0.0000000000) (42 . 0.0000000000) (91 . 0) (10 27.6421111602 68.3967000000) (40 . 0.0000000000) (41 . 0.0000000000) (42 . -0.4142135624) (91 . 0) (10 27.1421111602 68.8967000000) (40 . 0.0000000000) (41 . 0.0000000000) (42 . 0.0000000000) (91 . 0) (10 27.1421111602 69.0967000000) (40 . 0.0000000000) (41 . 0.0000000000) (42 . -0.4142135624) (91 . 0) (10 27.6421111602 69.5967000000) (40 . 0.0000000000) (41 . 0.0000000000) (42 . 0.0000000000) (91 . 0) (10 28.0421111602 69.5967000000) (40 . 0.0000000000) (41 . 0.0000000000) (42 . 0.4142135624) (91 . 0) (10 28.5421111602 70.0967000000) (40 . 0.0000000000) (41 . 0.0000000000) (42 . 0.0000000000) (91 . 0) (10 28.5421111602 70.7967000000) (40 . 0.0000000000) (41 . 0.0000000000) (42 . 0.4142135624) (91 . 0) (10 28.0421111602 71.2967000000) (40 . 0.0000000000) (41 . 0.0000000000) (42 . 0.0000000000) (91 . 0) (10 23.8421111602 71.2967000000) (40 . 0.0000000000) (41 . 0.0000000000) (42 . 0.4142135624) (91 . 0) (10 23.3421111602 70.7967000000) (40 . 0.0000000000) (41 . 0.0000000000) (42 . 0.0000000000) (91 . 0) (10 23.3421111602 70.0967000000) (40 . 0.0000000000) (41 . 0.0000000000) (42 . 0.4142135624) (91 . 0) (10 23.8421111602 69.5967000000) (40 . 0.0000000000) (41 . 0.0000000000) (42 . 0.0000000000) (91 . 0) (10 24.2421111602 69.5967000000) (40 . 0.0000000000) (41 . 0.0000000000) (42 . -0.4142135624) (91 . 0) (10 24.7421111602 69.0967000000) (40 . 0.0000000000) (41 . 0.0000000000) (42 . 0.0000000000) (91 . 0) (10 24.7421111602 68.8967000000) (40 . 0.0000000000) (41 . 0.0000000000) (42 . -0.4142135624) (91 . 0) (10 24.2421111602 68.3967000000) (40 . 0.0000000000) (41 . 0.0000000000) (42 . 0.0000000000) (91 . 0) (10 -0.3578888398 68.3967000000) (40 . 0.0000000000) (41 . 0.0000000000) (42 . 0.0000000000) (91 . 0) (10 -24.9578888398 68.3967000000) (40 . 0.0000000000) (41 . 0.0000000000) (42 . -0.4142135624) (91 . 0) (10 -25.4578888398 68.8967000000) (40 . 0.0000000000) (41 . 0.0000000000) (42 . 0.0000000000) (91 . 0) (10 -25.4578888398 69.0967000000) (40 . 0.0000000000) (41 . 0.0000000000) (42 . -0.4142135624) (91 . 0) (10 -24.9578888398 69.5967000000) (40 . 0.0000000000) (41 . 0.0000000000) (42 . 0.0000000000) (91 . 0) (10 -24.5578888398 69.5967000000) (40 . 0.0000000000) (41 . 0.0000000000) (42 . 0.4142135624) (91 . 0) (10 -24.0578888398 70.0967000000) (40 . 0.0000000000) (41 . 0.0000000000) (42 . 0.0000000000) (91 . 0) (10 -24.0578888398 70.7967000000) (40 . 0.0000000000) (41 . 0.0000000000) (42 . 0.4142135624) (91 . 0) (10 -24.5578888398 71.2967000000) (40 . 0.0000000000) (41 . 0.0000000000) (42 . 0.0000000000) (91 . 0) (10 -28.7578888398 71.2967000000) (40 . 0.0000000000) (41 . 0.0000000000) (42 . 0.4142135624) (91 . 0) (10 -29.2578888398 70.7967000000) (40 . 0.0000000000) (41 . 0.0000000000) (42 . 0.0000000000) (91 . 0) (10 -29.2578888398 70.0967000000) (40 . 0.0000000000) (41 . 0.0000000000) (42 . 0.4142135624) (91 . 0) (10 -28.7578888398 69.5967000000) (40 . 0.0000000000) (41 . 0.0000000000) (42 . 0.0000000000) (91 . 0) (10 -28.3578888398 69.5967000000) (40 . 0.0000000000) (41 . 0.0000000000) (42 . -0.4142135624) (91 . 0) (10 -27.8578888398 69.0967000000) (40 . 0.0000000000) (41 . 0.0000000000) (42 . 0.0000000000) (91 . 0) (10 -27.8578888398 68.8967000000) (40 . 0.0000000000) (41 . 0.0000000000) (42 . -0.4142135624) (91 . 0) (10 -28.3578888398 68.3967000000) (40 . 0.0000000000) (41 . 0.0000000000) (42 . 0.0000000000) (91 . 0) (10 -31.1578888398 68.3967000000) (40 . 0.0000000000) (41 . 0.0000000000) (42 . -0.4142135624) (91 . 0) (10 -31.6578888398 68.8967000000) (40 . 0.0000000000) (41 . 0.0000000000) (42 . 0.0000000000) (91 . 0) (10 -31.6578888398 72.8967000000) (40 . 0.0000000000) (41 . 0.0000000000) (42 . -0.4142135624) (91 . 0) (10 -31.1578888398 73.3967000000) (40 . 0.0000000000) (41 . 0.0000000000) (42 . 0.0000000000) (91 . 0) (10 -30.9578888398 73.3967000000) (40 . 0.0000000000) (41 . 0.0000000000) (42 . 0.4142135624) (91 . 0) (10 -30.4578888398 73.8967000000) (40 . 0.0000000000) (41 . 0.0000000000) (42 . 0.0000000000) (91 . 0) (10 -30.4578888398 75.7967000000) (40 . 0.0000000000) (41 . 0.0000000000) (42 . 0.4142135624) (91 . 0) (10 -30.7578888398 76.0967000000) (40 . 0.0000000000) (41 . 0.0000000000) (42 . 0.0000000000) (91 . 0) (10 -30.9578888398 76.0967000000) (40 . 0.0000000000) (41 . 0.0000000000) (42 . -0.5205670506) (91 . 0) (10 -31.1458273640 76.3651040286) (40 . 0.0000000000) (41 . 0.0000000000) (42 . 0.0000000000) (91 . 0) (10 -30.5261294436 78.0677100716) (40 . 0.0000000000) (41 . 0.0000000000) (42 . -0.3152987889) (91 . 0) (10 -30.0562831332 78.3967000000) (40 . 0.0000000000) (41 . 0.0000000000) (42 . 0.0000000000) (91 . 0) (10 -29.7578888398 78.3967000000) (40 . 0.0000000000) (41 . 0.0000000000) (42 . -0.4142135624) (91 . 0) (10 -29.2578888398 77.8967000000) (40 . 0.0000000000) (41 . 0.0000000000) (42 . 0.0000000000) (91 . 0) (10 -29.2578888398 73.8967000000) (40 . 0.0000000000) (41 . 0.0000000000) (42 . 0.4142135624) (91 . 0) (10 -28.7578888398 73.3967000000) (40 . 0.0000000000) (41 . 0.0000000000) (42 . 0.0000000000) (91 . 0) (10 -22.1578888398 73.3967000000) (40 . 0.0000000000) (41 . 0.0000000000) (42 . -0.4142135624) (91 . 0) (10 -21.6578888398 72.8967000000) (40 . 0.0000000000) (41 . 0.0000000000) (42 . 0.0000000000) (91 . 0) (10 -21.6578888398 71.8967000000) (40 . 0.0000000000) (41 . 0.0000000000) (42 . 0.4142135624) (91 . 0) (10 -21.1578888398 71.3967000000) (40 . 0.0000000000) (41 . 0.0000000000) (42 . 0.0000000000) (91 . 0) (10 -1.0235742648 71.3967000000) (40 . 0.0000000000) (41 . 0.0000000000) (42 . -0.1989123674) (91 . 0) (10 -0.8821529085 71.3381213562) (40 . 0.0000000000) (41 . 0.0000000000) (42 . 0.0000000000) (91 . 0) (10 -0.4993101960 70.9552786438) (40 . 0.0000000000) (41 . 0.0000000000) (42 . 0.1989123674) (91 . 0) (10 -0.3578888398 70.8967000000) (40 . 0.0000000000) (41 . 0.0000000000) (42 . 0.1989123674) (91 . 0) (10 -0.2164674836 70.9552786438) (40 . 0.0000000000) (41 . 0.0000000000) (42 . 0.0000000000) (91 . 0) (10 0.1663752289 71.3381213562) (40 . 0.0000000000) (41 . 0.0000000000) (42 . -0.1989123674) (91 . 0) (10 0.3077965851 71.3967000000) (40 . 0.0000000000) (41 . 0.0000000000) (42 . 0.0000000000) (91 . 0) (10 20.4421111602 71.3967000000) (40 . 0.0000000000) (41 . 0.0000000000) (42 . 0.4142135624) (91 . 0) (10 20.9421111602 71.8967000000) (40 . 0.0000000000) (41 . 0.0000000000) (42 . 0.0000000000) (91 . 0) (210 0.0000000000 0.0000000000 1.0000000000))
((0 . "LWPOLYLINE") (100 . "AcDbEntity") (67 . 0) (8 . "A-Window") (62 . 3) (6 . "Continuous") (100 . "AcDbPolyline") (90 . 44) (70 . 1) (43 . 0.0000000000) (38 . 0.0000000000) (39 . 0.0000000000) (10 23.6421111610 70.2966877930) (40 . 0.0000000000) (41 . 0.0000000000) (42 . 0.0000000000) (91 . 0) (10 23.6421111610 70.0967122070) (40 . 0.0000000000) (41 . 0.0000000000) (42 . 0.4142225008) (91 . 0) (10 24.0421111608 69.6967000000) (40 . 0.0000000000) (41 . 0.0000000000) (42 . 0.0000000000) (91 . 0) (10 24.2421111608 69.6967000000) (40 . 0.0000000000) (41 . 0.0000000000) (42 . -0.4142135624) (91 . 0) (10 24.8421111608 69.0967000000) (40 . 0.0000000000) (41 . 0.0000000000) (42 . 0.0000000000) (91 . 0) (10 24.8421111608 68.8967000000) (40 . 0.0000000000) (41 . 0.0000000000) (42 . -0.2513806714) (91 . 0) (10 24.5737736398 68.3967000000) (40 . 0.0000000000) (41 . 0.0000000000) (42 . 0.0000000000) (91 . 0) (10 22.8419369362 68.3967000000) (40 . 0.0000000000) (41 . 0.0000000000) (42 . 0.4142135624) (91 . 0) (10 22.3419369362 67.8967000000) (40 . 0.0000000000) (41 . 0.0000000000) (42 . 0.0000000000) (91 . 0) (10 22.3419369362 63.2967000000) (40 . 0.0000000000) (41 . 0.0000000000) (42 . 0.4142135624) (91 . 0) (10 22.8419369362 62.7967000000) (40 . 0.0000000000) (41 . 0.0000000000) (42 . 0.0000000000) (91 . 0) (10 23.0521408922 62.7967000000) (40 . 0.0000000000) (41 . 0.0000000000) (42 . 0.0000000000) (91 . 0) (10 23.1968257876 63.1989988506) (40 . 0.0000000000) (41 . 0.0000000000) (42 . 0.0000000000) (91 . 0) (10 23.5540632006 63.1989988506) (40 . 0.0000000000) (41 . 0.0000000000) (42 . 0.0000000000) (91 . 0) (10 23.6938075589 62.7967000000) (40 . 0.0000000000) (41 . 0.0000000000) (42 . 0.0000000000) (91 . 0) (10 24.3354742255 62.7967000000) (40 . 0.0000000000) (41 . 0.0000000000) (42 . 0.0000000000) (91 . 0) (10 24.4801591210 63.1989988506) (40 . 0.0000000000) (41 . 0.0000000000) (42 . 0.0000000000) (91 . 0) (10 24.8373965339 63.1989988506) (40 . 0.0000000000) (41 . 0.0000000000) (42 . 0.0000000000) (91 . 0) (10 24.9771408922 62.7967000000) (40 . 0.0000000000) (41 . 0.0000000000) (42 . 0.0000000000) (91 . 0) (10 25.6188075589 62.7967000000) (40 . 0.0000000000) (41 . 0.0000000000) (42 . 0.0000000000) (91 . 0) (10 25.7634924543 63.1989988506) (40 . 0.0000000000) (41 . 0.0000000000) (42 . 0.0000000000) (91 . 0) (10 26.1207298673 63.1989988506) (40 . 0.0000000000) (41 . 0.0000000000) (42 . 0.0000000000) (91 . 0) (10 26.2604742255 62.7967000000) (40 . 0.0000000000) (41 . 0.0000000000) (42 . 0.0000000000) (91 . 0) (10 26.9021408922 62.7967000000) (40 . 0.0000000000) (41 . 0.0000000000) (42 . 0.0000000000) (91 . 0) (10 27.0468257876 63.1989988506) (40 . 0.0000000000) (41 . 0.0000000000) (42 . 0.0000000000) (91 . 0) (10 27.4040632006 63.1989988506) (40 . 0.0000000000) (41 . 0.0000000000) (42 . 0.0000000000) (91 . 0) (10 27.5438075589 62.7967000000) (40 . 0.0000000000) (41 . 0.0000000000) (42 . 0.0000000000) (91 . 0) (10 28.1854742255 62.7967000000) (40 . 0.0000000000) (41 . 0.0000000000) (42 . 0.0000000000) (91 . 0) (10 28.3301591210 63.1989988506) (40 . 0.0000000000) (41 . 0.0000000000) (42 . 0.0000000000) (91 . 0) (10 28.6873965339 63.1989988506) (40 . 0.0000000000) (41 . 0.0000000000) (42 . 0.0000000000) (91 . 0) (10 28.8271408922 62.7967000000) (40 . 0.0000000000) (41 . 0.0000000000) (42 . 0.0000000000) (91 . 0) (10 29.0419369361 62.7967000000) (40 . 0.0000000000) (41 . 0.0000000000) (42 . 0.4142135624) (91 . 0) (10 29.5419369361 63.2967000000) (40 . 0.0000000000) (41 . 0.0000000000) (42 . 0.0000000000) (91 . 0) (10 29.5419369361 67.8967000000) (40 . 0.0000000000) (41 . 0.0000000000) (42 . 0.4142135624) (91 . 0) (10 29.0419369361 68.3967000000) (40 . 0.0000000000) (41 . 0.0000000000) (42 . 0.0000000000) (91 . 0) (10 27.3104486818 68.3967000000) (40 . 0.0000000000) (41 . 0.0000000000) (42 . -0.2513806714) (91 . 0) (10 27.0421111608 68.8967000000) (40 . 0.0000000000) (41 . 0.0000000000) (42 . 0.0000000000) (91 . 0) (10 27.0421111608 69.0967000000) (40 . 0.0000000000) (41 . 0.0000000000) (42 . -0.4142135624) (91 . 0) (10 27.6421111608 69.6967000000) (40 . 0.0000000000) (41 . 0.0000000000) (42 . 0.0000000000) (91 . 0) (10 27.8421111608 69.6967000000) (40 . 0.0000000000) (41 . 0.0000000000) (42 . 0.4142135624) (91 . 0) (10 28.2421111608 70.0967000000) (40 . 0.0000000000) (41 . 0.0000000000) (42 . 0.0000000000) (91 . 0) (10 28.2421111608 70.2967000000) (40 . 0.0000000000) (41 . 0.0000000000) (42 . 0.4142135624) (91 . 0) (10 27.8421111608 70.6967000000) (40 . 0.0000000000) (41 . 0.0000000000) (42 . 0.0000000000) (91 . 0) (10 24.0421111608 70.6967000000) (40 . 0.0000000000) (41 . 0.0000000000) (42 . 0.4142225008) (91 . 0) (210 0.0000000000 0.0000000000 1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 28.0969369362 67.3467000000) (40 . 0.0000000000) (41 . 0.0000000000) (42 . 0.0000000000) (91 . 0) (10 28.0969369362 64.2467000000) (40 . 0.0000000000) (41 . 0.0000000000) (42 . 0.0000000000) (91 . 0) (10 26.5969369362 64.2467000000) (40 . 0.0000000000) (41 . 0.0000000000) (42 . 0.0000000000) (91 . 0) (10 26.5969369362 67.3467000000) (40 . 0.0000000000) (41 . 0.0000000000) (42 . 0.0000000000) (91 . 0) (210 0.0000000000 0.0000000000 1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 25.2469369362 67.3467000000) (40 . 0.0000000000) (41 . 0.0000000000) (42 . 0.0000000000) (91 . 0) (10 25.2469369362 64.2467000000) (40 . 0.0000000000) (41 . 0.0000000000) (42 . 0.0000000000) (91 . 0) (10 23.7469369362 64.2467000000) (40 . 0.0000000000) (41 . 0.0000000000) (42 . 0.0000000000) (91 . 0) (10 23.7469369362 67.3467000000) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 44) (70 . 1) (43 . 0.0000000000) (38 . 0.0000000000) (39 . 0.0000000000) (10 -31.6578888398 91.8967000000) (40 . 0.0000000000) (41 . 0.0000000000) (42 . 0.0000000000) (91 . 0) (10 -31.6578888398 80.7967000000) (40 . 0.0000000000) (41 . 0.0000000000) (42 . 0.4142135624) (91 . 0) (10 -31.1578888398 80.2967000000) (40 . 0.0000000000) (41 . 0.0000000000) (42 . 0.0000000000) (91 . 0) (10 -29.1578888398 80.2967000000) (40 . 0.0000000000) (41 . 0.0000000000) (42 . -0.4142135624) (91 . 0) (10 -28.6578888398 79.7967000000) (40 . 0.0000000000) (41 . 0.0000000000) (42 . 0.0000000000) (91 . 0) (10 -28.6578888398 79.5967000000) (40 . 0.0000000000) (41 . 0.0000000000) (42 . -0.4142135624) (91 . 0) (10 -29.1578888398 79.0967000000) (40 . 0.0000000000) (41 . 0.0000000000) (42 . 0.0000000000) (91 . 0) (10 -31.1578888398 79.0967000000) (40 . 0.0000000000) (41 . 0.0000000000) (42 . 0.4142135624) (91 . 0) (10 -31.6578888398 78.5967000000) (40 . 0.0000000000) (41 . 0.0000000000) (42 . 0.0000000000) (91 . 0) (10 -31.6578888398 76.2967000000) (40 . 0.0000000000) (41 . 0.0000000000) (42 . 0.4142135624) (91 . 0) (10 -31.4578888398 76.0967000000) (40 . 0.0000000000) (41 . 0.0000000000) (42 . 0.0000000000) (91 . 0) (10 -30.7757356338 76.0967000000) (40 . 0.0000000000) (41 . 0.0000000000) (42 . -0.5522631265) (91 . 0) (10 -30.5954310223 75.8101537865) (40 . 0.0000000000) (41 . 0.0000000000) (42 . 0.0000000000) (91 . 0) (10 -31.6381934513 73.6377320594) (40 . 0.0000000000) (41 . 0.0000000000) (42 . 0.1123491485) (91 . 0) (10 -31.6578888398 73.5511858458) (40 . 0.0000000000) (41 . 0.0000000000) (42 . 0.0000000000) (91 . 0) (10 -31.6578888398 67.1967000000) (40 . 0.0000000000) (41 . 0.0000000000) (42 . -0.4142135624) (91 . 0) (10 -32.2578888398 66.5967000000) (40 . 0.0000000000) (41 . 0.0000000000) (42 . -0.4142135624) (91 . 0) (10 -32.8578888398 67.1967000000) (40 . 0.0000000000) (41 . 0.0000000000) (42 . 0.0000000000) (91 . 0) (10 -32.8578888398 93.0967000000) (40 . 0.0000000000) (41 . 0.0000000000) (42 . -0.4142135624) (91 . 0) (10 -32.3578888398 93.5967000000) (40 . 0.0000000000) (41 . 0.0000000000) (42 . 0.0000000000) (91 . 0) (10 -0.3578888398 93.5967000000) (40 . 0.0000000000) (41 . 0.0000000000) (42 . 0.0000000000) (91 . 0) (10 31.6421111602 93.5967000000) (40 . 0.0000000000) (41 . 0.0000000000) (42 . -0.4142135624) (91 . 0) (10 32.1421111602 93.0967000000) (40 . 0.0000000000) (41 . 0.0000000000) (42 . 0.0000000000) (91 . 0) (10 32.1421111602 67.1967000000) (40 . 0.0000000000) (41 . 0.0000000000) (42 . -0.4142135624) (91 . 0) (10 31.5421111602 66.5967000000) (40 . 0.0000000000) (41 . 0.0000000000) (42 . -0.4142135624) (91 . 0) (10 30.9421111602 67.1967000000) (40 . 0.0000000000) (41 . 0.0000000000) (42 . 0.0000000000) (91 . 0) (10 30.9421111602 73.5511858458) (40 . 0.0000000000) (41 . 0.0000000000) (42 . 0.1123491485) (91 . 0) (10 30.9224157717 73.6377320594) (40 . 0.0000000000) (41 . 0.0000000000) (42 . 0.0000000000) (91 . 0) (10 29.8796533427 75.8101537865) (40 . 0.0000000000) (41 . 0.0000000000) (42 . -0.5522631265) (91 . 0) (10 30.0599579542 76.0967000000) (40 . 0.0000000000) (41 . 0.0000000000) (42 . 0.0000000000) (91 . 0) (10 30.7421111602 76.0967000000) (40 . 0.0000000000) (41 . 0.0000000000) (42 . 0.4142135624) (91 . 0) (10 30.9421111602 76.2967000000) (40 . 0.0000000000) (41 . 0.0000000000) (42 . 0.0000000000) (91 . 0) (10 30.9421111602 78.5967000000) (40 . 0.0000000000) (41 . 0.0000000000) (42 . 0.4142135624) (91 . 0) (10 30.4421111602 79.0967000000) (40 . 0.0000000000) (41 . 0.0000000000) (42 . 0.0000000000) (91 . 0) (10 28.4421111602 79.0967000000) (40 . 0.0000000000) (41 . 0.0000000000) (42 . -0.4142135624) (91 . 0) (10 27.9421111602 79.5967000000) (40 . 0.0000000000) (41 . 0.0000000000) (42 . 0.0000000000) (91 . 0) (10 27.9421111602 79.7967000000) (40 . 0.0000000000) (41 . 0.0000000000) (42 . -0.4142135624) (91 . 0) (10 28.4421111602 80.2967000000) (40 . 0.0000000000) (41 . 0.0000000000) (42 . 0.0000000000) (91 . 0) (10 30.4421111602 80.2967000000) (40 . 0.0000000000) (41 . 0.0000000000) (42 . 0.4142135624) (91 . 0) (10 30.9421111602 80.7967000000) (40 . 0.0000000000) (41 . 0.0000000000) (42 . 0.0000000000) (91 . 0) (10 30.9421111602 91.8967000000) (40 . 0.0000000000) (41 . 0.0000000000) (42 . 0.4142135624) (91 . 0) (10 30.4421111602 92.3967000000) (40 . 0.0000000000) (41 . 0.0000000000) (42 . 0.0000000000) (91 . 0) (10 -0.3578888398 92.3967000000) (40 . 0.0000000000) (41 . 0.0000000000) (42 . 0.0000000000) (91 . 0) (10 -31.1578888398 92.3967000000) (40 . 0.0000000000) (41 . 0.0000000000) (42 . 0.4142135624) (91 . 0) (210 0.0000000000 0.0000000000 1.0000000000))
((0 . "LINE") (100 . "AcDbEntity") (67 . 0) (8 . "A-Window") (62 . 151) (6 . "Continuous") (100 . "AcDbLine") (10 -2.5828888395 59.8994120805 0.0000000000) (11 -2.5828888395 60.7929549452 0.0000000000) (210 0.0000000000 0.0000000000 1.0000000000))
((0 . "LINE") (100 . "AcDbEntity") (67 . 0) (8 . "A-Window") (62 . 151) (6 . "Continuous") (100 . "AcDbLine") (10 -2.5828888395 61.5694120805 0.0000000000) (11 -2.5828888395 62.4629549452 0.0000000000) (210 0.0000000000 0.0000000000 1.0000000000))
((0 . "LINE") (100 . "AcDbEntity") (67 . 0) (8 . "A-Window") (62 . 151) (6 . "Continuous") (100 . "AcDbLine") (10 -2.5828888395 56.5594120805 0.0000000000) (11 -2.5828888395 57.4529549452 0.0000000000) (210 0.0000000000 0.0000000000 1.0000000000))
((0 . "LINE") (100 . "AcDbEntity") (67 . 0) (8 . "A-Window") (62 . 151) (6 . "Continuous") (100 . "AcDbLine") (10 -2.5828888395 58.2294120805 0.0000000000) (11 -2.5828888395 59.1229549452 0.0000000000) (210 0.0000000000 0.0000000000 1.0000000000))
((0 . "LINE") (100 . "AcDbEntity") (67 . 0) (8 . "A-Window") (62 . 151) (6 . "Continuous") (100 . "AcDbLine") (10 1.8671111605 55.5896136866 0.0000000000) (11 1.8671111605 56.4831565513 0.0000000000) (210 0.0000000000 0.0000000000 1.0000000000))
((0 . "LINE") (100 . "AcDbEntity") (67 . 0) (8 . "A-Window") (62 . 151) (6 . "Continuous") (100 . "AcDbLine") (10 1.8671111605 57.2596136866 0.0000000000) (11 1.8671111605 58.1531565513 0.0000000000) (210 0.0000000000 0.0000000000 1.0000000000))
((0 . "LINE") (100 . "AcDbEntity") (67 . 0) (8 . "A-Window") (62 . 151) (6 . "Continuous") (100 . "AcDbLine") (10 1.8671111605 58.9296136866 0.0000000000) (11 1.8671111605 59.8231565513 0.0000000000) (210 0.0000000000 0.0000000000 1.0000000000))
((0 . "LINE") (100 . "AcDbEntity") (67 . 0) (8 . "A-Window") (62 . 151) (6 . "Continuous") (100 . "AcDbLine") (10 1.8671111605 60.5996136866 0.0000000000) (11 1.8671111605 61.4931565513 0.0000000000) (210 0.0000000000 0.0000000000 1.0000000000))
((0 . "LINE") (100 . "AcDbEntity") (67 . 0) (8 . "A-Window") (62 . 151) (6 . "Continuous") (100 . "AcDbLine") (10 1.8671111605 62.2696136866 0.0000000000) (11 1.8671111605 63.1631565513 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1.8671111605 57.2596136866) (40 . 0.0000000000) (41 . 0.0000000000) (42 . 0.0000000000) (91 . 0) (10 2.3921111605 56.8713851190) (40 . 0.0000000000) (41 . 0.0000000000) (42 . 0.0000000000) (91 . 0) (10 1.8671111605 56.4831565513) (40 . 0.0000000000) (41 . 0.0000000000) (42 . 0.0000000000) (91 . 0) (10 -2.5828888395 57.4529549452) (40 . 0.0000000000) (41 . 0.0000000000) (42 . 0.0000000000) (91 . 0) (10 -3.1078888395 57.8411835128) (40 . 0.0000000000) (41 . 0.0000000000) (42 . 0.0000000000) (91 . 0) (10 -2.5828888395 58.2294120805) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1.8671111605 60.5996136866) (40 . 0.0000000000) (41 . 0.0000000000) (42 . 0.0000000000) (91 . 0) (10 2.3921111605 60.2113851190) (40 . 0.0000000000) (41 . 0.0000000000) (42 . 0.0000000000) (91 . 0) (10 1.8671111605 59.8231565513) (40 . 0.0000000000) (41 . 0.0000000000) (42 . 0.0000000000) (91 . 0) (10 -2.5828888395 60.7929549452) (40 . 0.0000000000) (41 . 0.0000000000) (42 . 0.0000000000) (91 . 0) (10 -3.1078888395 61.1811835129) (40 . 0.0000000000) (41 . 0.0000000000) (42 . 0.0000000000) (91 . 0) (10 -2.5828888395 61.5694120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 -3.1078888395 59.5111835129 0.0000000000) (11 2.3921111605 58.5413851190 0.0000000000) (210 0.0000000000 0.0000000000 1.0000000000))
((0 . "LINE") (100 . "AcDbEntity") (67 . 0) (8 . "A-Window") (62 . 151) (6 . "Continuous") (100 . "AcDbLine") (10 -3.1078888395 61.1811835129 0.0000000000) (11 2.3921111605 60.2113851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1.8671111605 58.9296136866) (40 . 0.0000000000) (41 . 0.0000000000) (42 . 0.0000000000) (91 . 0) (10 2.3921111605 58.5413851190) (40 . 0.0000000000) (41 . 0.0000000000) (42 . 0.0000000000) (91 . 0) (10 1.8671111605 58.1531565513) (40 . 0.0000000000) (41 . 0.0000000000) (42 . 0.0000000000) (91 . 0) (10 -2.5828888395 59.1229549452) (40 . 0.0000000000) (41 . 0.0000000000) (42 . 0.0000000000) (91 . 0) (10 -3.1078888395 59.5111835129) (40 . 0.0000000000) (41 . 0.0000000000) (42 . 0.0000000000) (91 . 0) (10 -2.5828888395 59.8994120805) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1.8671111605 62.2696136866) (40 . 0.0000000000) (41 . 0.0000000000) (42 . 0.0000000000) (91 . 0) (10 2.3921111605 61.8813851190) (40 . 0.0000000000) (41 . 0.0000000000) (42 . 0.0000000000) (91 . 0) (10 1.8671111605 61.4931565513) (40 . 0.0000000000) (41 . 0.0000000000) (42 . 0.0000000000) (91 . 0) (10 -2.5828888395 62.4629549452) (40 . 0.0000000000) (41 . 0.0000000000) (42 . 0.0000000000) (91 . 0) (10 -3.1078888395 62.8511835129) (40 . 0.0000000000) (41 . 0.0000000000) (42 . 0.0000000000) (91 . 0) (10 -2.5828888395 63.2394120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 -3.1078888395 62.8511835129 0.0000000000) (11 2.3921111605 61.8813851190 0.0000000000) (210 0.0000000000 0.0000000000 1.0000000000))
((0 . "LINE") (100 . "AcDbEntity") (67 . 0) (8 . "A-Window") (62 . 151) (6 . "Continuous") (100 . "AcDbLine") (10 -3.1078888395 57.8411835128 0.0000000000) (11 2.3921111605 56.8713851190 0.0000000000) (210 0.0000000000 0.0000000000 1.0000000000))
((0 . "LINE") (100 . "AcDbEntity") (67 . 0) (8 . "A-Window") (62 . 151) (6 . "Continuous") (100 . "AcDbLine") (10 -2.5828888395 66.9194120805 0.0000000000) (11 -2.5828888395 67.8129549452 0.0000000000) (210 0.0000000000 0.0000000000 1.0000000000))
((0 . "LINE") (100 . "AcDbEntity") (67 . 0) (8 . "A-Window") (62 . 151) (6 . "Continuous") (100 . "AcDbLine") (10 -2.5828888395 61.9094120805 0.0000000000) (11 -2.5828888395 62.8029549452 0.0000000000) (210 0.0000000000 0.0000000000 1.0000000000))
((0 . "LINE") (100 . "AcDbEntity") (67 . 0) (8 . "A-Window") (62 . 151) (6 . "Continuous") (100 . "AcDbLine") (10 -2.5828888395 63.5794120805 0.0000000000) (11 -2.5828888395 64.4729549452 0.0000000000) (210 0.0000000000 0.0000000000 1.0000000000))
((0 . "LINE") (100 . "AcDbEntity") (67 . 0) (8 . "A-Window") (62 . 151) (6 . "Continuous") (100 . "AcDbLine") (10 -2.5828888395 65.2494120805 0.0000000000) (11 -2.5828888395 66.1429549452 0.0000000000) (210 0.0000000000 0.0000000000 1.0000000000))
((0 . "LINE") (100 . "AcDbEntity") (67 . 0) (8 . "A-Window") (62 . 151) (6 . "Continuous") (100 . "AcDbLine") (10 -2.5828888395 71.9294120805 0.0000000000) (11 -2.5828888395 72.8229549452 0.0000000000) (210 0.0000000000 0.0000000000 1.0000000000))
((0 . "LINE") (100 . "AcDbEntity") (67 . 0) (8 . "A-Window") (62 . 151) (6 . "Continuous") (100 . "AcDbLine") (10 -2.5828888395 70.2594120805 0.0000000000) (11 -2.5828888395 71.1529549452 0.0000000000) (210 0.0000000000 0.0000000000 1.0000000000))
((0 . "LINE") (100 . "AcDbEntity") (67 . 0) (8 . "A-Window") (62 . 151) (6 . "Continuous") (100 . "AcDbLine") (10 -2.5828888395 68.5894120805 0.0000000000) (11 -2.5828888395 69.4829549452 0.0000000000) (210 0.0000000000 0.0000000000 1.0000000000))
((0 . "LINE") (100 . "AcDbEntity") (67 . 0) (8 . "A-Window") (62 . 151) (6 . "Continuous") (100 . "AcDbLine") (10 1.8671111605 60.9396136866 0.0000000000) (11 1.8671111605 61.8331565513 0.0000000000) (210 0.0000000000 0.0000000000 1.0000000000))
((0 . "LINE") (100 . "AcDbEntity") (67 . 0) (8 . "A-Window") (62 . 151) (6 . "Continuous") (100 . "AcDbLine") (10 1.8671111605 65.9496136866 0.0000000000) (11 1.8671111605 66.8431565513 0.0000000000) (210 0.0000000000 0.0000000000 1.0000000000))
((0 . "LINE") (100 . "AcDbEntity") (67 . 0) (8 . "A-Window") (62 . 151) (6 . "Continuous") (100 . "AcDbLine") (10 1.8671111605 67.6196136866 0.0000000000) (11 1.8671111605 68.5131565513 0.0000000000) (210 0.0000000000 0.0000000000 1.0000000000))
((0 . "LINE") (100 . "AcDbEntity") (67 . 0) (8 . "A-Window") (62 . 151) (6 . "Continuous") (100 . "AcDbLine") (10 1.8671111605 62.6096136866 0.0000000000) (11 1.8671111605 63.5031565513 0.0000000000) (210 0.0000000000 0.0000000000 1.0000000000))
((0 . "LINE") (100 . "AcDbEntity") (67 . 0) (8 . "A-Window") (62 . 151) (6 . "Continuous") (100 . "AcDbLine") (10 1.8671111605 64.2796136866 0.0000000000) (11 1.8671111605 65.1731565513 0.0000000000) (210 0.0000000000 0.0000000000 1.0000000000))
((0 . "LINE") (100 . "AcDbEntity") (67 . 0) (8 . "A-Window") (62 . 151) (6 . "Continuous") (100 . "AcDbLine") (10 1.8671111605 69.2896136866 0.0000000000) (11 1.8671111605 70.1831565513 0.0000000000) (210 0.0000000000 0.0000000000 1.0000000000))
((0 . "LINE") (100 . "AcDbEntity") (67 . 0) (8 . "A-Window") (62 . 151) (6 . "Continuous") (100 . "AcDbLine") (10 1.8671111605 70.9596136866 0.0000000000) (11 1.8671111605 71.8531565513 0.0000000000) (210 0.0000000000 0.0000000000 1.0000000000))
((0 . "LINE") (100 . "AcDbEntity") (67 . 0) (8 . "A-Window") (62 . 151) (6 . "Continuous") (100 . "AcDbLine") (10 1.8671111605 72.6296136866 0.0000000000) (11 1.8671111605 72.8917774718 0.0000000000) (210 0.0000000000 0.0000000000 1.0000000000))
((0 . "LINE") (100 . "AcDbEntity") (67 . 0) (8 . "A-Window") (62 . 151) (6 . "Continuous") (100 . "AcDbLine") (10 -3.1078888395 63.1911835129 0.0000000000) (11 2.3921111605 62.2213851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1.8671111605 62.6096136866) (40 . 0.0000000000) (41 . 0.0000000000) (42 . 0.0000000000) (91 . 0) (10 2.3921111605 62.2213851190) (40 . 0.0000000000) (41 . 0.0000000000) (42 . 0.0000000000) (91 . 0) (10 1.8671111605 61.8331565513) (40 . 0.0000000000) (41 . 0.0000000000) (42 . 0.0000000000) (91 . 0) (10 -2.5828888395 62.8029549452) (40 . 0.0000000000) (41 . 0.0000000000) (42 . 0.0000000000) (91 . 0) (10 -3.1078888395 63.1911835129) (40 . 0.0000000000) (41 . 0.0000000000) (42 . 0.0000000000) (91 . 0) (10 -2.5828888395 63.5794120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 -3.1078888395 64.8611835129 0.0000000000) (11 2.3921111605 63.8913851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1.8671111605 64.2796136866) (40 . 0.0000000000) (41 . 0.0000000000) (42 . 0.0000000000) (91 . 0) (10 2.3921111605 63.8913851190) (40 . 0.0000000000) (41 . 0.0000000000) (42 . 0.0000000000) (91 . 0) (10 1.8671111605 63.5031565513) (40 . 0.0000000000) (41 . 0.0000000000) (42 . 0.0000000000) (91 . 0) (10 -2.5828888395 64.4729549452) (40 . 0.0000000000) (41 . 0.0000000000) (42 . 0.0000000000) (91 . 0) (10 -3.1078888395 64.8611835129) (40 . 0.0000000000) (41 . 0.0000000000) (42 . 0.0000000000) (91 . 0) (10 -2.5828888395 65.2494120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 -3.1078888395 66.5311835129 0.0000000000) (11 2.3921111605 65.5613851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1.8671111605 65.9496136866) (40 . 0.0000000000) (41 . 0.0000000000) (42 . 0.0000000000) (91 . 0) (10 2.3921111605 65.5613851190) (40 . 0.0000000000) (41 . 0.0000000000) (42 . 0.0000000000) (91 . 0) (10 1.8671111605 65.1731565513) (40 . 0.0000000000) (41 . 0.0000000000) (42 . 0.0000000000) (91 . 0) (10 -2.5828888395 66.1429549452) (40 . 0.0000000000) (41 . 0.0000000000) (42 . 0.0000000000) (91 . 0) (10 -3.1078888395 66.5311835129) (40 . 0.0000000000) (41 . 0.0000000000) (42 . 0.0000000000) (91 . 0) (10 -2.5828888395 66.9194120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 -3.1078888395 68.2011835129 0.0000000000) (11 2.3921111605 67.2313851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1.8671111605 67.6196136866) (40 . 0.0000000000) (41 . 0.0000000000) (42 . 0.0000000000) (91 . 0) (10 2.3921111605 67.2313851190) (40 . 0.0000000000) (41 . 0.0000000000) (42 . 0.0000000000) (91 . 0) (10 1.8671111605 66.8431565513) (40 . 0.0000000000) (41 . 0.0000000000) (42 . 0.0000000000) (91 . 0) (10 -2.5828888395 67.8129549452) (40 . 0.0000000000) (41 . 0.0000000000) (42 . 0.0000000000) (91 . 0) (10 -3.1078888395 68.2011835129) (40 . 0.0000000000) (41 . 0.0000000000) (42 . 0.0000000000) (91 . 0) (10 -2.5828888395 68.5894120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 -3.1078888395 69.8711835129 0.0000000000) (11 2.3921111605 68.9013851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1.8671111605 69.2896136866) (40 . 0.0000000000) (41 . 0.0000000000) (42 . 0.0000000000) (91 . 0) (10 2.3921111605 68.9013851190) (40 . 0.0000000000) (41 . 0.0000000000) (42 . 0.0000000000) (91 . 0) (10 1.8671111605 68.5131565513) (40 . 0.0000000000) (41 . 0.0000000000) (42 . 0.0000000000) (91 . 0) (10 -2.5828888395 69.4829549452) (40 . 0.0000000000) (41 . 0.0000000000) (42 . 0.0000000000) (91 . 0) (10 -3.1078888395 69.8711835129) (40 . 0.0000000000) (41 . 0.0000000000) (42 . 0.0000000000) (91 . 0) (10 -2.5828888395 70.2594120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 -3.1078888395 71.5411835129 0.0000000000) (11 2.3921111605 70.5713851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1.8671111605 70.9596136866) (40 . 0.0000000000) (41 . 0.0000000000) (42 . 0.0000000000) (91 . 0) (10 2.3921111605 70.5713851190) (40 . 0.0000000000) (41 . 0.0000000000) (42 . 0.0000000000) (91 . 0) (10 1.8671111605 70.1831565513) (40 . 0.0000000000) (41 . 0.0000000000) (42 . 0.0000000000) (91 . 0) (10 -2.5828888395 71.1529549452) (40 . 0.0000000000) (41 . 0.0000000000) (42 . 0.0000000000) (91 . 0) (10 -3.1078888395 71.5411835129) (40 . 0.0000000000) (41 . 0.0000000000) (42 . 0.0000000000) (91 . 0) (10 -2.5828888395 71.9294120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 -1.2964471656 72.8917774718 0.0000000000) (11 2.3921111605 72.2413851190 0.0000000000) (210 0.0000000000 0.0000000000 1.0000000000))
((0 . "LWPOLYLINE") (100 . "AcDbEntity") (67 . 0) (8 . "A-Window") (62 . 151) (6 . "Continuous") (100 . "AcDbPolyline") (90 . 6) (70 . 0) (43 . 0.0000000000) (38 . 0.0000000000) (39 . 0.0000000000) (10 0.6641509873 72.8917774718) (40 . 0.0000000000) (41 . 0.0000000000) (42 . 0.0000000000) (91 . 0) (10 1.8671111605 72.6296136866) (40 . 0.0000000000) (41 . 0.0000000000) (42 . 0.0000000000) (91 . 0) (10 2.3921111605 72.2413851190) (40 . 0.0000000000) (41 . 0.0000000000) (42 . 0.0000000000) (91 . 0) (10 1.8671111605 71.8531565513) (40 . 0.0000000000) (41 . 0.0000000000) (42 . 0.0000000000) (91 . 0) (10 -2.5828888395 72.8229549452) (40 . 0.0000000000) (41 . 0.0000000000) (42 . 0.0000000000) (91 . 0) (10 -2.6759572777 72.8917774718) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 4) (70 . 1) (43 . 0.0000000000) (38 . 0.0000000000) (39 . 0.0000000000) (10 -5.8578888395 73.8917774718) (40 . 0.0000000000) (41 . 0.0000000000) (42 . 0.0000000000) (91 . 0) (10 -5.8578888395 72.8917774718) (40 . 0.0000000000) (41 . 0.0000000000) (42 . 0.0000000000) (91 . 0) (10 5.1421111605 72.8917774718) (40 . 0.0000000000) (41 . 0.0000000000) (42 . 0.0000000000) (91 . 0) (10 5.1421111605 73.8917774718) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 -3.1078888395 61.5211835129 0.0000000000) (11 2.3921111605 63.5513851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1.8671111605 60.9396136866) (40 . 0.0000000000) (41 . 0.0000000000) (42 . 0.0000000000) (91 . 0) (10 2.3921111605 63.5513851190) (40 . 0.0000000000) (41 . 0.0000000000) (42 . 0.0000000000) (91 . 0) (10 1.8671111605 63.1631565513) (40 . 0.0000000000) (41 . 0.0000000000) (42 . 0.0000000000) (91 . 0) (10 -2.5828888395 61.1329549452) (40 . 0.0000000000) (41 . 0.0000000000) (42 . 0.0000000000) (91 . 0) (10 -3.1078888395 61.5211835129) (40 . 0.0000000000) (41 . 0.0000000000) (42 . 0.0000000000) (91 . 0) (10 -2.5828888395 61.9094120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 -2.5828888395 63.2394120805 0.0000000000) (11 -2.5828888395 61.1329549452 0.0000000000) (210 0.0000000000 0.0000000000 1.0000000000))
((0 . "LINE") (100 . "AcDbEntity") (67 . 0) (8 . "A-Window") (62 . 151) (6 . "Continuous") (100 . "AcDbLine") (10 -3.8219904546 78.2917774718 0.0000000000) (11 3.1062127756 78.2917774718 0.0000000000) (210 0.0000000000 0.0000000000 1.0000000000))
((0 . "LINE") (100 . "AcDbEntity") (67 . 0) (8 . "A-Window") (62 . 151) (6 . "CENTER2") (100 . "AcDbLine") (10 -0.3578888395 37.5451762388 0.0000000000) (11 -0.3578888395 81.5869711621 0.0000000000) (210 0.0000000000 0.0000000000 1.0000000000))
((0 . "LINE") (100 . "AcDbEntity") (67 . 0) (8 . "A-Window") (62 . 151) (6 . "Continuous") (100 . "AcDbLine") (10 -2.6672899163 77.2917774717 0.0000000000) (11 -2.6672899163 73.8917774718 0.0000000000) (210 0.0000000000 0.0000000000 1.0000000000))
((0 . "LINE") (100 . "AcDbEntity") (67 . 0) (8 . "A-Window") (62 . 151) (6 . "Continuous") (100 . "AcDbLine") (10 1.9515122373 77.2917774717 0.0000000000) (11 1.9515122373 73.8917774718 0.0000000000) (210 0.0000000000 0.0000000000 1.0000000000))
((0 . "LWPOLYLINE") (100 . "AcDbEntity") (67 . 0) (8 . "A-Window") (62 . 151) (6 . "Continuous") (100 . "AcDbPolyline") (90 . 6) (70 . 0) (43 . 0.0000000000) (38 . 0.0000000000) (39 . 0.0000000000) (10 4.2609133140 73.8917774718) (40 . 0.0000000000) (41 . 0.0000000000) (42 . 0.0000000000) (91 . 0) (10 4.2609133140 77.2917774717) (40 . 0.0000000000) (41 . 0.0000000000) (42 . 0.8660254038) (91 . 0) (10 1.9515122373 77.2917774717) (40 . 0.0000000000) (41 . 0.0000000000) (42 . 0.4330127019) (91 . 0) (10 -2.6672899163 77.2917774717) (40 . 0.0000000000) (41 . 0.0000000000) (42 . 0.8660254038) (91 . 0) (10 -4.9766909930 77.2917774717) (40 . 0.0000000000) (41 . 0.0000000000) (42 . 0.0000000000) (91 . 0) (10 -4.9766909930 73.8917774718) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 4) (70 . 1) (43 . 0.0000000000) (38 . 0.0000000000) (39 . 0.0000000000) (10 -2.5828888395 42.6957453328) (40 . 0.0000000000) (41 . 0.0000000000) (42 . 0.0000000000) (91 . 0) (10 -0.9713231013 42.5675818646) (40 . 0.0000000000) (41 . 0.0000000000) (42 . 0.0000000000) (91 . 0) (10 -2.5828888395 43.0839739004) (40 . 0.0000000000) (41 . 0.0000000000) (42 . 0.0000000000) (91 . 0) (10 -2.7903888395 42.8898596166) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 -2.7903888395 42.8898596166 0.0000000000) (11 -0.9713231013 42.5675818646 0.0000000000) (210 0.0000000000 0.0000000000 1.0000000000))
((0 . "LINE") (100 . "AcDbEntity") (67 . 0) (8 . "A-Window") (62 . 151) (6 . "Continuous") (100 . "AcDbLine") (10 -2.5828888395 48.2094120805 0.0000000000) (11 -2.5828888395 49.1029549452 0.0000000000) (210 0.0000000000 0.0000000000 1.0000000000))
((0 . "LINE") (100 . "AcDbEntity") (67 . 0) (8 . "A-Window") (62 . 151) (6 . "Continuous") (100 . "AcDbLine") (10 -2.5828888395 56.5594120805 0.0000000000) (11 -2.5828888395 57.4529549452 0.0000000000) (210 0.0000000000 0.0000000000 1.0000000000))
((0 . "LINE") (100 . "AcDbEntity") (67 . 0) (8 . "A-Window") (62 . 151) (6 . "Continuous") (100 . "AcDbLine") (10 -2.8941388395 44.5782406548 0.0000000000) (11 -1.6210499782 44.3526917877 0.0000000000) (210 0.0000000000 0.0000000000 1.0000000000))
((0 . "LINE") (100 . "AcDbEntity") (67 . 0) (8 . "A-Window") (62 . 151) (6 . "Continuous") (100 . "AcDbLine") (10 -2.5828888395 44.8694120805 0.0000000000) (11 -2.5828888395 45.7629549452 0.0000000000) (210 0.0000000000 0.0000000000 1.0000000000))
((0 . "LWPOLYLINE") (100 . "AcDbEntity") (67 . 0) (8 . "A-Window") (62 . 151) (6 . "Continuous") (100 . "AcDbPolyline") (90 . 5) (70 . 0) (43 . 0.0000000000) (38 . 0.0000000000) (39 . 0.0000000000) (10 -1.5110249293 44.0504004504) (40 . 0.0000000000) (41 . 0.0000000000) (42 . 0.0000000000) (91 . 0) (10 -2.5828888395 44.2870692290) (40 . 0.0000000000) (41 . 0.0000000000) (42 . 0.0000000000) (91 . 0) (10 -2.8941388395 44.5782406548) (40 . 0.0000000000) (41 . 0.0000000000) (42 . 0.0000000000) (91 . 0) (10 -2.5828888395 44.8694120805) (40 . 0.0000000000) (41 . 0.0000000000) (42 . 0.0000000000) (91 . 0) (10 -1.7415027540 44.6836330695) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 -2.5828888395 46.5394120805 0.0000000000) (11 -2.5828888395 47.4329549452 0.0000000000) (210 0.0000000000 0.0000000000 1.0000000000))
((0 . "LINE") (100 . "AcDbEntity") (67 . 0) (8 . "A-Window") (62 . 151) (6 . "Continuous") (100 . "AcDbLine") (10 -2.5828888395 43.0839739004 0.0000000000) (11 -2.5828888395 44.2870692290 0.0000000000) (210 0.0000000000 0.0000000000 1.0000000000))
((0 . "LINE") (100 . "AcDbEntity") (67 . 0) (8 . "A-Window") (62 . 151) (6 . "Continuous") (100 . "AcDbLine") (10 1.8671111605 44.1620742983 0.0000000000) (11 1.8671111605 44.7931565513 0.0000000000) (210 0.0000000000 0.0000000000 1.0000000000))
((0 . "LINE") (100 . "AcDbEntity") (67 . 0) (8 . "A-Window") (62 . 151) (6 . "Continuous") (100 . "AcDbLine") (10 1.8671111605 45.5696136866 0.0000000000) (11 1.8671111605 46.4631565513 0.0000000000) (210 0.0000000000 0.0000000000 1.0000000000))
((0 . "LINE") (100 . "AcDbEntity") (67 . 0) (8 . "A-Window") (62 . 151) (6 . "Continuous") (100 . "AcDbLine") (10 1.8671111605 47.2396136866 0.0000000000) (11 1.8671111605 48.1331565513 0.0000000000) (210 0.0000000000 0.0000000000 1.0000000000))
((0 . "LINE") (100 . "AcDbEntity") (67 . 0) (8 . "A-Window") (62 . 151) (6 . "Continuous") (100 . "AcDbLine") (10 1.8671111605 57.2596136866 0.0000000000) (11 1.8671111605 58.1531565513 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1.8671111605 45.5696136866) (40 . 0.0000000000) (41 . 0.0000000000) (42 . 0.0000000000) (91 . 0) (10 2.3921111605 45.1813851190) (40 . 0.0000000000) (41 . 0.0000000000) (42 . 0.0000000000) (91 . 0) (10 1.8671111605 44.7931565513) (40 . 0.0000000000) (41 . 0.0000000000) (42 . 0.0000000000) (91 . 0) (10 -2.5828888395 45.7629549452) (40 . 0.0000000000) (41 . 0.0000000000) (42 . 0.0000000000) (91 . 0) (10 -3.1078888395 46.1511835129) (40 . 0.0000000000) (41 . 0.0000000000) (42 . 0.0000000000) (91 . 0) (10 -2.5828888395 46.5394120805) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1.8671111605 55.5896136866) (40 . 0.0000000000) (41 . 0.0000000000) (42 . 0.0000000000) (91 . 0) (10 2.3921111605 55.2013851190) (40 . 0.0000000000) (41 . 0.0000000000) (42 . 0.0000000000) (91 . 0) (10 1.8671111605 54.8131565513) (40 . 0.0000000000) (41 . 0.0000000000) (42 . 0.0000000000) (91 . 0) (10 -2.5828888395 55.7829549452) (40 . 0.0000000000) (41 . 0.0000000000) (42 . 0.0000000000) (91 . 0) (10 -3.1078888395 56.1711835129) (40 . 0.0000000000) (41 . 0.0000000000) (42 . 0.0000000000) (91 . 0) (10 -2.5828888395 56.5594120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 -3.1078888395 47.8211835129 0.0000000000) (11 2.3921111605 46.8513851190 0.0000000000) (210 0.0000000000 0.0000000000 1.0000000000))
((0 . "LINE") (100 . "AcDbEntity") (67 . 0) (8 . "A-Window") (62 . 151) (6 . "Continuous") (100 . "AcDbLine") (10 -3.1078888395 56.1711835129 0.0000000000) (11 2.3921111605 55.2013851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1.8671111605 47.2396136866) (40 . 0.0000000000) (41 . 0.0000000000) (42 . 0.0000000000) (91 . 0) (10 2.3921111605 46.8513851190) (40 . 0.0000000000) (41 . 0.0000000000) (42 . 0.0000000000) (91 . 0) (10 1.8671111605 46.4631565513) (40 . 0.0000000000) (41 . 0.0000000000) (42 . 0.0000000000) (91 . 0) (10 -2.5828888395 47.4329549452) (40 . 0.0000000000) (41 . 0.0000000000) (42 . 0.0000000000) (91 . 0) (10 -3.1078888395 47.8211835129) (40 . 0.0000000000) (41 . 0.0000000000) (42 . 0.0000000000) (91 . 0) (10 -2.5828888395 48.2094120805) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1.8671111605 57.2596136866) (40 . 0.0000000000) (41 . 0.0000000000) (42 . 0.0000000000) (91 . 0) (10 2.3921111605 56.8713851190) (40 . 0.0000000000) (41 . 0.0000000000) (42 . 0.0000000000) (91 . 0) (10 1.8671111605 56.4831565513) (40 . 0.0000000000) (41 . 0.0000000000) (42 . 0.0000000000) (91 . 0) (10 -2.5828888395 57.4529549452) (40 . 0.0000000000) (41 . 0.0000000000) (42 . 0.0000000000) (91 . 0) (10 -3.1078888395 57.8411835128) (40 . 0.0000000000) (41 . 0.0000000000) (42 . 0.0000000000) (91 . 0) (10 -2.5828888395 58.2294120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 -3.1078888395 57.8411835128 0.0000000000) (11 2.3921111605 56.8713851190 0.0000000000) (210 0.0000000000 0.0000000000 1.0000000000))
((0 . "LINE") (100 . "AcDbEntity") (67 . 0) (8 . "A-Window") (62 . 151) (6 . "Continuous") (100 . "AcDbLine") (10 -3.1078888395 46.1511835129 0.0000000000) (11 2.3921111605 45.1813851190 0.0000000000) (210 0.0000000000 0.0000000000 1.0000000000))
((0 . "LWPOLYLINE") (100 . "AcDbEntity") (67 . 0) (8 . "A-Window") (62 . 151) (6 . "Continuous") (100 . "AcDbPolyline") (90 . 10) (70 . 0) (43 . 0.0000000000) (38 . 0.0000000000) (39 . 0.0000000000) (10 -2.5828888395 42.6957453328) (40 . 0.0000000000) (41 . 0.0000000000) (42 . 0.0000000000) (91 . 0) (10 -2.5828888395 41.0687741511) (40 . 0.0000000000) (41 . 0.0000000000) (42 . 0.0000000000) (91 . 0) (10 -0.3578888395 39.2017774718) (40 . 0.0000000000) (41 . 0.0000000000) (42 . 0.0000000000) (91 . 0) (10 1.8671111605 41.0687741511) (40 . 0.0000000000) (41 . 0.0000000000) (42 . 0.0000000000) (91 . 0) (10 1.8671111605 43.5797314468) (40 . 0.0000000000) (41 . 0.0000000000) (42 . 0.0000000000) (91 . 0) (10 2.1783611605 43.8709028725) (40 . 0.0000000000) (41 . 0.0000000000) (42 . 0.0000000000) (91 . 0) (10 1.8671111605 44.1620742983) (40 . 0.0000000000) (41 . 0.0000000000) (42 . 0.2138820884) (91 . 0) (10 -1.7415027540 44.6836330695) (40 . 0.0000000000) (41 . 0.0000000000) (42 . 0.0000000000) (91 . 0) (10 0.1106380000 39.5949181700) (40 . 0.0000000000) (41 . 0.0000000000) (42 . 0.2315249815) (91 . 0) (10 -2.5828888395 41.0687741511) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 -2.5828888395 59.8994120805 0.0000000000) (11 -2.5828888395 60.7929549452 0.0000000000) (210 0.0000000000 0.0000000000 1.0000000000))
((0 . "LINE") (100 . "AcDbEntity") (67 . 0) (8 . "A-Window") (62 . 151) (6 . "Continuous") (100 . "AcDbLine") (10 -2.5828888395 61.5694120805 0.0000000000) (11 -2.5828888395 62.4629549452 0.0000000000) (210 0.0000000000 0.0000000000 1.0000000000))
((0 . "LINE") (100 . "AcDbEntity") (67 . 0) (8 . "A-Window") (62 . 151) (6 . "Continuous") (100 . "AcDbLine") (10 -2.5828888395 63.2394120805 0.0000000000) (11 -2.5828888395 61.1329549452 0.0000000000) (210 0.0000000000 0.0000000000 1.0000000000))
((0 . "LINE") (100 . "AcDbEntity") (67 . 0) (8 . "A-Window") (62 . 151) (6 . "Continuous") (100 . "AcDbLine") (10 1.8671111605 58.9296136866 0.0000000000) (11 1.8671111605 59.8231565513 0.0000000000) (210 0.0000000000 0.0000000000 1.0000000000))
((0 . "LINE") (100 . "AcDbEntity") (67 . 0) (8 . "A-Window") (62 . 151) (6 . "Continuous") (100 . "AcDbLine") (10 1.8671111605 60.5996136866 0.0000000000) (11 1.8671111605 61.4931565513 0.0000000000) (210 0.0000000000 0.0000000000 1.0000000000))
((0 . "LINE") (100 . "AcDbEntity") (67 . 0) (8 . "A-Window") (62 . 151) (6 . "Continuous") (100 . "AcDbLine") (10 1.8671111605 62.2696136866 0.0000000000) (11 1.8671111605 63.1631565513 0.0000000000) (210 0.0000000000 0.0000000000 1.0000000000))
((0 . "LINE") (100 . "AcDbEntity") (67 . 0) (8 . "A-Window") (62 . 151) (6 . "Continuous") (100 . "AcDbLine") (10 -3.1078888395 61.1811835129 0.0000000000) (11 2.3921111605 60.2113851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1.8671111605 60.5996136866) (40 . 0.0000000000) (41 . 0.0000000000) (42 . 0.0000000000) (91 . 0) (10 2.3921111605 60.2113851190) (40 . 0.0000000000) (41 . 0.0000000000) (42 . 0.0000000000) (91 . 0) (10 1.8671111605 59.8231565513) (40 . 0.0000000000) (41 . 0.0000000000) (42 . 0.0000000000) (91 . 0) (10 -2.5828888395 60.7929549452) (40 . 0.0000000000) (41 . 0.0000000000) (42 . 0.0000000000) (91 . 0) (10 -3.1078888395 61.1811835129) (40 . 0.0000000000) (41 . 0.0000000000) (42 . 0.0000000000) (91 . 0) (10 -2.5828888395 61.5694120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 -3.1078888395 62.8511835129 0.0000000000) (11 2.3921111605 61.8813851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1.8671111605 62.2696136866) (40 . 0.0000000000) (41 . 0.0000000000) (42 . 0.0000000000) (91 . 0) (10 2.3921111605 61.8813851190) (40 . 0.0000000000) (41 . 0.0000000000) (42 . 0.0000000000) (91 . 0) (10 1.8671111605 61.4931565513) (40 . 0.0000000000) (41 . 0.0000000000) (42 . 0.0000000000) (91 . 0) (10 -2.5828888395 62.4629549452) (40 . 0.0000000000) (41 . 0.0000000000) (42 . 0.0000000000) (91 . 0) (10 -3.1078888395 62.8511835129) (40 . 0.0000000000) (41 . 0.0000000000) (42 . 0.0000000000) (91 . 0) (10 -2.5828888395 63.2394120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 -3.1078888395 61.5211835129 0.0000000000) (11 2.3921111605 63.5513851190 0.0000000000) (210 0.0000000000 0.0000000000 1.0000000000))
((0 . "LINE") (100 . "AcDbEntity") (67 . 0) (8 . "A-Window") (62 . 151) (6 . "Continuous") (100 . "AcDbLine") (10 -3.1078888395 59.5111835129 0.0000000000) (11 2.3921111605 58.5413851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1.8671111605 58.9296136866) (40 . 0.0000000000) (41 . 0.0000000000) (42 . 0.0000000000) (91 . 0) (10 2.3921111605 58.5413851190) (40 . 0.0000000000) (41 . 0.0000000000) (42 . 0.0000000000) (91 . 0) (10 1.8671111605 58.1531565513) (40 . 0.0000000000) (41 . 0.0000000000) (42 . 0.0000000000) (91 . 0) (10 -2.5828888395 59.1229549452) (40 . 0.0000000000) (41 . 0.0000000000) (42 . 0.0000000000) (91 . 0) (10 -3.1078888395 59.5111835129) (40 . 0.0000000000) (41 . 0.0000000000) (42 . 0.0000000000) (91 . 0) (10 -2.5828888395 59.8994120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 -2.5828888395 58.2294120805 0.0000000000) (11 -2.5828888395 59.1229549452 0.0000000000) (210 0.0000000000 0.0000000000 1.0000000000))
((0 . "LINE") (100 . "AcDbEntity") (67 . 0) (8 . "A-Window") (62 . 151) (6 . "Continuous") (100 . "AcDbLine") (10 -2.5828888395 54.8894120805 0.0000000000) (11 -2.5828888395 55.7829549452 0.0000000000) (210 0.0000000000 0.0000000000 1.0000000000))
((0 . "LINE") (100 . "AcDbEntity") (67 . 0) (8 . "A-Window") (62 . 151) (6 . "Continuous") (100 . "AcDbLine") (10 1.8671111605 53.9196136866 0.0000000000) (11 1.8671111605 54.8131565513 0.0000000000) (210 0.0000000000 0.0000000000 1.0000000000))
((0 . "LINE") (100 . "AcDbEntity") (67 . 0) (8 . "A-Window") (62 . 151) (6 . "Continuous") (100 . "AcDbLine") (10 -2.5828888395 54.8894120805 0.0000000000) (11 -2.5828888395 55.7829549452 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1.8671111605 53.9196136866) (40 . 0.0000000000) (41 . 0.0000000000) (42 . 0.0000000000) (91 . 0) (10 2.3921111605 53.5313851190) (40 . 0.0000000000) (41 . 0.0000000000) (42 . 0.0000000000) (91 . 0) (10 1.8671111605 53.1431565513) (40 . 0.0000000000) (41 . 0.0000000000) (42 . 0.0000000000) (91 . 0) (10 -2.5828888395 54.1129549452) (40 . 0.0000000000) (41 . 0.0000000000) (42 . 0.0000000000) (91 . 0) (10 -3.1078888395 54.5011835129) (40 . 0.0000000000) (41 . 0.0000000000) (42 . 0.0000000000) (91 . 0) (10 -2.5828888395 54.8894120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 -3.1078888395 54.5011835129 0.0000000000) (11 2.3921111605 53.5313851190 0.0000000000) (210 0.0000000000 0.0000000000 1.0000000000))
((0 . "LINE") (100 . "AcDbEntity") (67 . 0) (8 . "A-Window") (62 . 151) (6 . "Continuous") (100 . "AcDbLine") (10 -2.5828888395 53.2194120805 0.0000000000) (11 -2.5828888395 54.1129549452 0.0000000000) (210 0.0000000000 0.0000000000 1.0000000000))
((0 . "LINE") (100 . "AcDbEntity") (67 . 0) (8 . "A-Window") (62 . 151) (6 . "Continuous") (100 . "AcDbLine") (10 1.8671111605 52.2496136866 0.0000000000) (11 1.8671111605 53.1431565513 0.0000000000) (210 0.0000000000 0.0000000000 1.0000000000))
((0 . "LINE") (100 . "AcDbEntity") (67 . 0) (8 . "A-Window") (62 . 151) (6 . "Continuous") (100 . "AcDbLine") (10 -2.5828888395 53.2194120805 0.0000000000) (11 -2.5828888395 54.1129549452 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1.8671111605 52.2496136866) (40 . 0.0000000000) (41 . 0.0000000000) (42 . 0.0000000000) (91 . 0) (10 2.3921111605 51.8613851190) (40 . 0.0000000000) (41 . 0.0000000000) (42 . 0.0000000000) (91 . 0) (10 1.8671111605 51.4731565513) (40 . 0.0000000000) (41 . 0.0000000000) (42 . 0.0000000000) (91 . 0) (10 -2.5828888395 52.4429549452) (40 . 0.0000000000) (41 . 0.0000000000) (42 . 0.0000000000) (91 . 0) (10 -3.1078888395 52.8311835129) (40 . 0.0000000000) (41 . 0.0000000000) (42 . 0.0000000000) (91 . 0) (10 -2.5828888395 53.2194120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 -3.1078888395 52.8311835129 0.0000000000) (11 2.3921111605 51.8613851190 0.0000000000) (210 0.0000000000 0.0000000000 1.0000000000))
((0 . "LINE") (100 . "AcDbEntity") (67 . 0) (8 . "A-Window") (62 . 151) (6 . "Continuous") (100 . "AcDbLine") (10 -7.3578888395 71.3967000000 0.0000000000) (11 -8.8578888395 71.3967000000 0.0000000000) (210 0.0000000000 0.0000000000 1.0000000000))
((0 . "LINE") (100 . "AcDbEntity") (67 . 0) (8 . "A-Window") (62 . 151) (6 . "Continuous") (100 . "AcDbLine") (10 -7.3578888395 72.8917774718 0.0000000000) (11 -7.3578888395 71.3967000000 0.0000000000) (210 0.0000000000 0.0000000000 1.0000000000))
((0 . "LINE") (100 . "AcDbEntity") (67 . 0) (8 . "A-Window") (62 . 151) (6 . "Continuous") (100 . "AcDbLine") (10 -5.8177271261 72.8917774718 0.0000000000) (11 -7.3578888395 72.8917774718 0.0000000000) (210 0.0000000000 0.0000000000 1.0000000000))
((0 . "LINE") (100 . "AcDbEntity") (67 . 0) (8 . "A-Window") (62 . 151) (6 . "Continuous") (100 . "AcDbLine") (10 6.6421111605 71.3967000000 0.0000000000) (11 6.6421111605 72.8917774718 0.0000000000) (210 0.0000000000 0.0000000000 1.0000000000))
((0 . "LINE") (100 . "AcDbEntity") (67 . 0) (8 . "A-Window") (62 . 151) (6 . "Continuous") (100 . "AcDbLine") (10 8.1421111605 71.3967000000 0.0000000000) (11 6.6421111605 71.3967000000 0.0000000000) (210 0.0000000000 0.0000000000 1.0000000000))
((0 . "LWPOLYLINE") (100 . "AcDbEntity") (67 . 0) (8 . "A-Window") (62 . 151) (6 . "Continuous") (100 . "AcDbPolyline") (90 . 4) (70 . 1) (43 . 0.0000000000) (38 . 0.0000000000) (39 . 0.0000000000) (10 -7.3578888395 71.3967000000) (40 . 0.0000000000) (41 . 0.0000000000) (42 . 0.0000000000) (91 . 0) (10 6.6421111605 71.3967000000) (40 . 0.0000000000) (41 . 0.0000000000) (42 . 0.0000000000) (91 . 0) (10 6.6421111605 72.8917774718) (40 . 0.0000000000) (41 . 0.0000000000) (42 . 0.0000000000) (91 . 0) (10 -7.3578888395 72.8917774718) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 -2.5828888395 51.5494120805 0.0000000000) (11 -2.5828888395 52.4429549452 0.0000000000) (210 0.0000000000 0.0000000000 1.0000000000))
((0 . "LINE") (100 . "AcDbEntity") (67 . 0) (8 . "A-Window") (62 . 151) (6 . "Continuous") (100 . "AcDbLine") (10 1.8671111605 50.5796136866 0.0000000000) (11 1.8671111605 51.4731565513 0.0000000000) (210 0.0000000000 0.0000000000 1.0000000000))
((0 . "LINE") (100 . "AcDbEntity") (67 . 0) (8 . "A-Window") (62 . 151) (6 . "Continuous") (100 . "AcDbLine") (10 -2.5828888395 51.5494120805 0.0000000000) (11 -2.5828888395 52.4429549452 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1.8671111605 50.5796136866) (40 . 0.0000000000) (41 . 0.0000000000) (42 . 0.0000000000) (91 . 0) (10 2.3921111605 50.1913851190) (40 . 0.0000000000) (41 . 0.0000000000) (42 . 0.0000000000) (91 . 0) (10 1.8671111605 49.8031565513) (40 . 0.0000000000) (41 . 0.0000000000) (42 . 0.0000000000) (91 . 0) (10 -2.5828888395 50.7729549452) (40 . 0.0000000000) (41 . 0.0000000000) (42 . 0.0000000000) (91 . 0) (10 -3.1078888395 51.1611835129) (40 . 0.0000000000) (41 . 0.0000000000) (42 . 0.0000000000) (91 . 0) (10 -2.5828888395 51.5494120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 -3.1078888395 51.1611835129 0.0000000000) (11 2.3921111605 50.1913851190 0.0000000000) (210 0.0000000000 0.0000000000 1.0000000000))
((0 . "LINE") (100 . "AcDbEntity") (67 . 0) (8 . "A-Window") (62 . 151) (6 . "Continuous") (100 . "AcDbLine") (10 -2.5828888395 49.8794120805 0.0000000000) (11 -2.5828888395 50.7729549452 0.0000000000) (210 0.0000000000 0.0000000000 1.0000000000))
((0 . "LINE") (100 . "AcDbEntity") (67 . 0) (8 . "A-Window") (62 . 151) (6 . "Continuous") (100 . "AcDbLine") (10 1.8671111605 48.9096136866 0.0000000000) (11 1.8671111605 49.8031565513 0.0000000000) (210 0.0000000000 0.0000000000 1.0000000000))
((0 . "LINE") (100 . "AcDbEntity") (67 . 0) (8 . "A-Window") (62 . 151) (6 . "Continuous") (100 . "AcDbLine") (10 -2.5828888395 49.8794120805 0.0000000000) (11 -2.5828888395 50.7729549452 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1.8671111605 48.9096136866) (40 . 0.0000000000) (41 . 0.0000000000) (42 . 0.0000000000) (91 . 0) (10 2.3921111605 48.5213851190) (40 . 0.0000000000) (41 . 0.0000000000) (42 . 0.0000000000) (91 . 0) (10 1.8671111605 48.1331565513) (40 . 0.0000000000) (41 . 0.0000000000) (42 . 0.0000000000) (91 . 0) (10 -2.5828888395 49.1029549452) (40 . 0.0000000000) (41 . 0.0000000000) (42 . 0.0000000000) (91 . 0) (10 -3.1078888395 49.4911835129) (40 . 0.0000000000) (41 . 0.0000000000) (42 . 0.0000000000) (91 . 0) (10 -2.5828888395 49.8794120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 -3.1078888395 49.4911835129 0.0000000000) (11 2.3921111605 48.5213851190 0.0000000000) (210 0.0000000000 0.0000000000 1.0000000000))
((0 . "ARC") (100 . "AcDbEntity") (67 . 0) (8 . "A-Window") (62 . 151) (6 . "Continuous") (100 . "AcDbCircle") (10 42.8123962027 66.7859023315 0.0000000000) (40 . 10.6781898097) (210 0.0000000000 0.0000000000 1.0000000000) (100 . "AcDbArc") (50 . 3.1031124361) (51 . -2.7687983156))
((0 . "LWPOLYLINE") (100 . "AcDbEntity") (67 . 0) (8 . "A-Window") (62 . 151) (6 . "Continuous") (370 . -3) (100 . "AcDbPolyline") (90 . 7) (70 . 0) (43 . 0.0000000000) (38 . 0.0000000000) (39 . 0.0000000000) (10 -12.1110622970 31.0817739862) (40 . 0.0000000000) (41 . 0.0000000000) (42 . 0.0000000000) (91 . 0) (10 -11.4298946284 31.2693893928) (40 . 0.0000000000) (41 . 0.0000000000) (42 . 0.0000000000) (91 . 0) (10 -12.1110622970 32.1851406910) (40 . 0.0000000000) (41 . 0.0000000000) (42 . 0.0000000000) (91 . 0) (10 -15.4689947926 33.7798758823) (40 . 0.0000000000) (41 . 0.0000000000) (42 . 0.0000000000) (91 . 0) (10 -16.1501624612 33.7922604757) (40 . 0.0000000000) (41 . 0.0000000000) (42 . 0.0000000000) (91 . 0) (10 -15.4689947926 32.8765091775) (40 . 0.0000000000) (41 . 0.0000000000) (42 . 0.0000000000) (91 . 0) (10 -12.0971869492 31.0743579422) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (370 . -3) (100 . "AcDbPolyline") (90 . 2) (70 . 0) (43 . 0.0000000000) (38 . 0.0000000000) (39 . 0.0000000000) (10 -11.4298946284 31.2693893928) (40 . 0.0000000000) (41 . 0.0000000000) (42 . 0.0000000000) (91 . 0) (10 -16.1501624612 33.7922604757) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (370 . -3) (100 . "AcDbPolyline") (90 . 2) (70 . 0) (43 . 0.0000000000) (38 . 0.0000000000) (39 . 0.0000000000) (10 -12.0183904041 21.4597508267) (40 . 0.0000000000) (41 . 0.0000000000) (42 . 0.0000000000) (91 . 0) (10 -15.9314443604 23.5511852584) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (370 . -3) (100 . "AcDbPolyline") (90 . 5) (70 . 0) (43 . 0.0000000000) (38 . 0.0000000000) (39 . 0.0000000000) (10 -16.1341341495 27.0637825200) (40 . 0.0000000000) (41 . 0.0000000000) (42 . 0.0000000000) (91 . 0) (10 -15.4529664810 27.2513979266) (40 . 0.0000000000) (41 . 0.0000000000) (42 . 0.0000000000) (91 . 0) (10 -12.0950339853 25.4566627353) (40 . 0.0000000000) (41 . 0.0000000000) (42 . 0.0000000000) (91 . 0) (10 -11.4138663168 24.5409114371) (40 . 0.0000000000) (41 . 0.0000000000) (42 . 0.0000000000) (91 . 0) (10 -12.0950339853 24.3532960304) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (370 . -3) (100 . "AcDbPolyline") (90 . 4) (70 . 0) (43 . 0.0000000000) (38 . 0.0000000000) (39 . 0.0000000000) (10 -12.0811586375 24.3458799865) (40 . 0.0000000000) (41 . 0.0000000000) (42 . 0.0000000000) (91 . 0) (10 -15.4529664810 26.1480312217) (40 . 0.0000000000) (41 . 0.0000000000) (42 . 0.0000000000) (91 . 0) (10 -16.1341341495 27.0637825200) (40 . 0.0000000000) (41 . 0.0000000000) (42 . 0.0000000000) (91 . 0) (10 -11.4138663168 24.5409114371) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (370 . -3) (100 . "AcDbPolyline") (90 . 2) (70 . 0) (43 . 0.0000000000) (38 . 0.0000000000) (39 . 0.0000000000) (10 -12.0950339853 27.6694253066) (40 . 0.0000000000) (41 . 0.0000000000) (42 . 0.0000000000) (91 . 0) (10 -11.4138663168 27.8570407132) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (370 . -3) (100 . "AcDbPolyline") (90 . 7) (70 . 0) (43 . 0.0000000000) (38 . 0.0000000000) (39 . 0.0000000000) (10 -16.1341341495 30.3799117961) (40 . 0.0000000000) (41 . 0.0000000000) (42 . 0.0000000000) (91 . 0) (10 -11.4138663168 27.8570407132) (40 . 0.0000000000) (41 . 0.0000000000) (42 . 0.0000000000) (91 . 0) (10 -12.0950339853 28.7727920115) (40 . 0.0000000000) (41 . 0.0000000000) (42 . 0.0000000000) (91 . 0) (10 -15.4529664810 30.5675272028) (40 . 0.0000000000) (41 . 0.0000000000) (42 . 0.0000000000) (91 . 0) (10 -16.1341341495 30.3799117961) (40 . 0.0000000000) (41 . 0.0000000000) (42 . 0.0000000000) (91 . 0) (10 -15.4529664810 29.4641604979) (40 . 0.0000000000) (41 . 0.0000000000) (42 . 0.0000000000) (91 . 0) (10 -12.0811586375 27.6620092627) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (370 . -3) (100 . "AcDbPolyline") (90 . 7) (70 . 0) (43 . 0.0000000000) (38 . 0.0000000000) (39 . 0.0000000000) (10 -15.2665929357 23.7561959660) (40 . 0.0000000000) (41 . 0.0000000000) (42 . 0.0000000000) (91 . 0) (10 -15.9477606042 23.5685805594) (40 . 0.0000000000) (41 . 0.0000000000) (42 . 0.0000000000) (91 . 0) (10 -14.8937778481 22.4448937926) (40 . 0.0000000000) (41 . 0.0000000000) (42 . 0.0000000000) (91 . 0) (10 -13.0073147160 21.4366240389) (40 . 0.0000000000) (41 . 0.0000000000) (42 . 0.0000000000) (91 . 0) (10 -12.0183904041 21.4597508267) (40 . 0.0000000000) (41 . 0.0000000000) (42 . 0.0000000000) (91 . 0) (10 -12.6995580726 22.3755021249) (40 . 0.0000000000) (41 . 0.0000000000) (42 . 0.0000000000) (91 . 0) (10 -15.2773036000 23.7532459058) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (370 . -3) (100 . "AcDbPolyline") (90 . 2) (70 . 0) (43 . 0.0000000000) (38 . 0.0000000000) (39 . 0.0000000000) (10 -9.7679917319 35.4966999996) (40 . 0.0000000000) (41 . 0.0000000000) (42 . 0.0000000000) (91 . 0) (10 -9.7679917319 36.5591518613) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 5) (70 . 1) (43 . 0.0000000000) (38 . 0.0000000000) (39 . 0.0000000000) (10 -15.4708531380 24.3384639426) (40 . 0.0000000000) (41 . 0.0000000000) (42 . 0.0000000000) (91 . 0) (10 -15.4548248263 35.4966999996) (40 . 0.0000000000) (41 . 0.0000000000) (42 . 0.0000000000) (91 . 0) (10 -12.0811586375 35.4966999996) (40 . 0.0000000000) (41 . 0.0000000000) (42 . 0.0000000000) (91 . 0) (10 -12.0971869492 24.3384639426) (40 . 0.0000000000) (41 . 0.0000000000) (42 . 0.0000000000) (91 . 0) (10 -13.8890502300 18.7758203153) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (370 . -3) (100 . "AcDbPolyline") (90 . 8) (70 . 1) (43 . 0.0000000000) (38 . 0.0000000000) (39 . 0.0000000000) (10 -17.7679917319 36.8650963037) (40 . 0.0000000000) (41 . 0.0000000000) (42 . -0.1594650997) (91 . 0) (10 -14.2028394419 38.2950135099) (40 . 0.0000000000) (41 . 0.0000000000) (42 . 0.0000000000) (91 . 0) (10 -14.2028394419 37.0168757213) (40 . 0.0000000000) (41 . 0.0000000000) (42 . 0.0000000000) (91 . 0) (10 -13.2521168727 37.0168757213) (40 . 0.0000000000) (41 . 0.0000000000) (42 . 0.0000000000) (91 . 0) (10 -13.2521168727 38.2837089403) (40 . 0.0000000000) (41 . 0.0000000000) (42 . -0.1569326025) (91 . 0) (10 -9.7679917319 36.8095064766) (40 . 0.0000000000) (41 . 0.0000000000) (42 . 0.0000000000) (91 . 0) (10 -9.7679917319 35.4966999996) (40 . 0.0000000000) (41 . 0.0000000000) (42 . 0.0000000000) (91 . 0) (10 -17.7679917319 35.4966999996) (40 . 0.0000000000) (41 . 0.0000000000) (42 . 0.0000000000) (91 . 0) (210 0.0000000000 0.0000000000 1.0000000000))
((0 . "LWPOLYLINE") (100 . "AcDbEntity") (67 . 0) (8 . "A-Window") (62 . 3) (6 . "Continuous") (100 . "AcDbPolyline") (90 . 44) (70 . 1) (43 . 0.0000000000) (38 . 0.0000000000) (39 . 0.0000000000) (10 24.3642583620 70.2966877930) (40 . 0.0000000000) (41 . 0.0000000000) (42 . 0.0000000000) (91 . 0) (10 24.3642583620 70.0967122071) (40 . 0.0000000000) (41 . 0.0000000000) (42 . 0.4142225008) (91 . 0) (10 24.7642583619 69.6967000001) (40 . 0.0000000000) (41 . 0.0000000000) (42 . 0.0000000000) (91 . 0) (10 24.9642583619 69.6967000001) (40 . 0.0000000000) (41 . 0.0000000000) (42 . -0.4142135624) (91 . 0) (10 25.5642583619 69.0967000001) (40 . 0.0000000000) (41 . 0.0000000000) (42 . 0.0000000000) (91 . 0) (10 25.5642583619 68.8967000001) (40 . 0.0000000000) (41 . 0.0000000000) (42 . -0.2513806714) (91 . 0) (10 25.2959208409 68.3967000001) (40 . 0.0000000000) (41 . 0.0000000000) (42 . 0.0000000000) (91 . 0) (10 23.5640841373 68.3967000001) (40 . 0.0000000000) (41 . 0.0000000000) (42 . 0.4142135624) (91 . 0) (10 23.0640841373 67.8967000001) (40 . 0.0000000000) (41 . 0.0000000000) (42 . 0.0000000000) (91 . 0) (10 23.0640841373 63.2967000001) (40 . 0.0000000000) (41 . 0.0000000000) (42 . 0.4142135624) (91 . 0) (10 23.5640841373 62.7967000001) (40 . 0.0000000000) (41 . 0.0000000000) (42 . 0.0000000000) (91 . 0) (10 23.7742880933 62.7967000001) (40 . 0.0000000000) (41 . 0.0000000000) (42 . 0.0000000000) (91 . 0) (10 23.9189729887 63.1989988507) (40 . 0.0000000000) (41 . 0.0000000000) (42 . 0.0000000000) (91 . 0) (10 24.2762104017 63.1989988507) (40 . 0.0000000000) (41 . 0.0000000000) (42 . 0.0000000000) (91 . 0) (10 24.4159547600 62.7967000001) (40 . 0.0000000000) (41 . 0.0000000000) (42 . 0.0000000000) (91 . 0) (10 25.0576214266 62.7967000001) (40 . 0.0000000000) (41 . 0.0000000000) (42 . 0.0000000000) (91 . 0) (10 25.2023063220 63.1989988507) (40 . 0.0000000000) (41 . 0.0000000000) (42 . 0.0000000000) (91 . 0) (10 25.5595437350 63.1989988507) (40 . 0.0000000000) (41 . 0.0000000000) (42 . 0.0000000000) (91 . 0) (10 25.6992880933 62.7967000001) (40 . 0.0000000000) (41 . 0.0000000000) (42 . 0.0000000000) (91 . 0) (10 26.3409547600 62.7967000001) (40 . 0.0000000000) (41 . 0.0000000000) (42 . 0.0000000000) (91 . 0) (10 26.4856396554 63.1989988507) (40 . 0.0000000000) (41 . 0.0000000000) (42 . 0.0000000000) (91 . 0) (10 26.8428770684 63.1989988507) (40 . 0.0000000000) (41 . 0.0000000000) (42 . 0.0000000000) (91 . 0) (10 26.9826214266 62.7967000001) (40 . 0.0000000000) (41 . 0.0000000000) (42 . 0.0000000000) (91 . 0) (10 27.6242880933 62.7967000001) (40 . 0.0000000000) (41 . 0.0000000000) (42 . 0.0000000000) (91 . 0) (10 27.7689729887 63.1989988507) (40 . 0.0000000000) (41 . 0.0000000000) (42 . 0.0000000000) (91 . 0) (10 28.1262104017 63.1989988507) (40 . 0.0000000000) (41 . 0.0000000000) (42 . 0.0000000000) (91 . 0) (10 28.2659547600 62.7967000001) (40 . 0.0000000000) (41 . 0.0000000000) (42 . 0.0000000000) (91 . 0) (10 28.9076214266 62.7967000001) (40 . 0.0000000000) (41 . 0.0000000000) (42 . 0.0000000000) (91 . 0) (10 29.0523063221 63.1989988507) (40 . 0.0000000000) (41 . 0.0000000000) (42 . 0.0000000000) (91 . 0) (10 29.4095437350 63.1989988507) (40 . 0.0000000000) (41 . 0.0000000000) (42 . 0.0000000000) (91 . 0) (10 29.5492880933 62.7967000001) (40 . 0.0000000000) (41 . 0.0000000000) (42 . 0.0000000000) (91 . 0) (10 29.7640841372 62.7967000001) (40 . 0.0000000000) (41 . 0.0000000000) (42 . 0.4142135624) (91 . 0) (10 30.2640841372 63.2967000001) (40 . 0.0000000000) (41 . 0.0000000000) (42 . 0.0000000000) (91 . 0) (10 30.2640841372 67.8967000001) (40 . 0.0000000000) (41 . 0.0000000000) (42 . 0.4142135624) (91 . 0) (10 29.7640841372 68.3967000001) (40 . 0.0000000000) (41 . 0.0000000000) (42 . 0.0000000000) (91 . 0) (10 28.0325958828 68.3967000001) (40 . 0.0000000000) (41 . 0.0000000000) (42 . -0.2513806714) (91 . 0) (10 27.7642583619 68.8967000001) (40 . 0.0000000000) (41 . 0.0000000000) (42 . 0.0000000000) (91 . 0) (10 27.7642583619 69.0967000001) (40 . 0.0000000000) (41 . 0.0000000000) (42 . -0.4142135624) (91 . 0) (10 28.3642583619 69.6967000001) (40 . 0.0000000000) (41 . 0.0000000000) (42 . 0.0000000000) (91 . 0) (10 28.5642583619 69.6967000001) (40 . 0.0000000000) (41 . 0.0000000000) (42 . 0.4142135624) (91 . 0) (10 28.9642583619 70.0967000001) (40 . 0.0000000000) (41 . 0.0000000000) (42 . 0.0000000000) (91 . 0) (10 28.9642583619 70.2967000001) (40 . 0.0000000000) (41 . 0.0000000000) (42 . 0.4142135624) (91 . 0) (10 28.5642583619 70.6967000001) (40 . 0.0000000000) (41 . 0.0000000000) (42 . 0.0000000000) (91 . 0) (10 24.7642583619 70.6967000001) (40 . 0.0000000000) (41 . 0.0000000000) (42 . 0.4142225008) (91 . 0) (210 0.0000000000 0.0000000000 -1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 28.8190841373 67.3467000001) (40 . 0.0000000000) (41 . 0.0000000000) (42 . 0.0000000000) (91 . 0) (10 28.8190841373 64.2467000001) (40 . 0.0000000000) (41 . 0.0000000000) (42 . 0.0000000000) (91 . 0) (10 27.3190841373 64.2467000001) (40 . 0.0000000000) (41 . 0.0000000000) (42 . 0.0000000000) (91 . 0) (10 27.3190841373 67.3467000001) (40 . 0.0000000000) (41 . 0.0000000000) (42 . 0.0000000000) (91 . 0) (210 0.0000000000 0.0000000000 -1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 25.9690841372 67.3467000001) (40 . 0.0000000000) (41 . 0.0000000000) (42 . 0.0000000000) (91 . 0) (10 25.9690841372 64.2467000001) (40 . 0.0000000000) (41 . 0.0000000000) (42 . 0.0000000000) (91 . 0) (10 24.4690841372 64.2467000001) (40 . 0.0000000000) (41 . 0.0000000000) (42 . 0.0000000000) (91 . 0) (10 24.4690841372 67.3467000001) (40 . 0.0000000000) (41 . 0.0000000000) (42 . 0.0000000000) (91 . 0) (210 0.0000000000 0.0000000000 -1.0000000000))
((0 . "LINE") (100 . "AcDbEntity") (67 . 0) (8 . "A-Window") (62 . 151) (6 . "Continuous") (100 . "AcDbLine") (10 -32.8676567472 62.3966999996 0.0000000000) (11 -32.8676567472 67.1967000011 0.0000000000) (210 0.0000000000 0.0000000000 1.0000000000))
((0 . "ARC") (100 . "AcDbEntity") (67 . 0) (8 . "A-Window") (62 . 151) (6 . "Continuous") (100 . "AcDbCircle") (10 42.8123962027 38.2074976685 0.0000000000) (40 . 10.6781898097) (210 0.0000000000 0.0000000000 1.0000000000) (100 . "AcDbArc") (50 . 2.7687983156) (51 . -3.1031124361))
((0 . "LWPOLYLINE") (100 . "AcDbEntity") (67 . 0) (8 . "A-Window") (62 . 3) (6 . "Continuous") (100 . "AcDbPolyline") (90 . 44) (70 . 1) (43 . 0.0000000000) (38 . 0.0000000000) (39 . 0.0000000000) (10 -25.0469016035 34.5713089269) (40 . 0.0000000000) (41 . 0.0000000000) (42 . 0.0000000000) (91 . 0) (10 -25.0469016035 34.7712845128) (40 . 0.0000000000) (41 . 0.0000000000) (42 . 0.4142225008) (91 . 0) (10 -25.4469016033 35.1712967198) (40 . 0.0000000000) (41 . 0.0000000000) (42 . 0.0000000000) (91 . 0) (10 -25.6469016033 35.1712967198) (40 . 0.0000000000) (41 . 0.0000000000) (42 . -0.4142135624) (91 . 0) (10 -26.2469016033 35.7712967198) (40 . 0.0000000000) (41 . 0.0000000000) (42 . 0.0000000000) (91 . 0) (10 -26.2469016033 35.9712967198) (40 . 0.0000000000) (41 . 0.0000000000) (42 . -0.2513806714) (91 . 0) (10 -25.9785640824 36.4712967198) (40 . 0.0000000000) (41 . 0.0000000000) (42 . 0.0000000000) (91 . 0) (10 -24.2467273787 36.4712967198) (40 . 0.0000000000) (41 . 0.0000000000) (42 . 0.4142135624) (91 . 0) (10 -23.7467273787 36.9712967198) (40 . 0.0000000000) (41 . 0.0000000000) (42 . 0.0000000000) (91 . 0) (10 -23.7467273787 41.5712967198) (40 . 0.0000000000) (41 . 0.0000000000) (42 . 0.4142135624) (91 . 0) (10 -24.2467273787 42.0712967198) (40 . 0.0000000000) (41 . 0.0000000000) (42 . 0.0000000000) (91 . 0) (10 -24.4569313347 42.0712967198) (40 . 0.0000000000) (41 . 0.0000000000) (42 . 0.0000000000) (91 . 0) (10 -24.6016162302 41.6689978692) (40 . 0.0000000000) (41 . 0.0000000000) (42 . 0.0000000000) (91 . 0) (10 -24.9588536432 41.6689978692) (40 . 0.0000000000) (41 . 0.0000000000) (42 . 0.0000000000) (91 . 0) (10 -25.0985980014 42.0712967198) (40 . 0.0000000000) (41 . 0.0000000000) (42 . 0.0000000000) (91 . 0) (10 -25.7402646681 42.0712967198) (40 . 0.0000000000) (41 . 0.0000000000) (42 . 0.0000000000) (91 . 0) (10 -25.8849495635 41.6689978692) (40 . 0.0000000000) (41 . 0.0000000000) (42 . 0.0000000000) (91 . 0) (10 -26.2421869765 41.6689978692) (40 . 0.0000000000) (41 . 0.0000000000) (42 . 0.0000000000) (91 . 0) (10 -26.3819313348 42.0712967198) (40 . 0.0000000000) (41 . 0.0000000000) (42 . 0.0000000000) (91 . 0) (10 -27.0235980014 42.0712967198) (40 . 0.0000000000) (41 . 0.0000000000) (42 . 0.0000000000) (91 . 0) (10 -27.1682828968 41.6689978692) (40 . 0.0000000000) (41 . 0.0000000000) (42 . 0.0000000000) (91 . 0) (10 -27.5255203098 41.6689978692) (40 . 0.0000000000) (41 . 0.0000000000) (42 . 0.0000000000) (91 . 0) (10 -27.6652646681 42.0712967198) (40 . 0.0000000000) (41 . 0.0000000000) (42 . 0.0000000000) (91 . 0) (10 -28.3069313347 42.0712967198) (40 . 0.0000000000) (41 . 0.0000000000) (42 . 0.0000000000) (91 . 0) (10 -28.4516162302 41.6689978692) (40 . 0.0000000000) (41 . 0.0000000000) (42 . 0.0000000000) (91 . 0) (10 -28.8088536432 41.6689978692) (40 . 0.0000000000) (41 . 0.0000000000) (42 . 0.0000000000) (91 . 0) (10 -28.9485980014 42.0712967198) (40 . 0.0000000000) (41 . 0.0000000000) (42 . 0.0000000000) (91 . 0) (10 -29.5902646681 42.0712967198) (40 . 0.0000000000) (41 . 0.0000000000) (42 . 0.0000000000) (91 . 0) (10 -29.7349495635 41.6689978692) (40 . 0.0000000000) (41 . 0.0000000000) (42 . 0.0000000000) (91 . 0) (10 -30.0921869765 41.6689978692) (40 . 0.0000000000) (41 . 0.0000000000) (42 . 0.0000000000) (91 . 0) (10 -30.2319313347 42.0712967198) (40 . 0.0000000000) (41 . 0.0000000000) (42 . 0.0000000000) (91 . 0) (10 -30.4467273787 42.0712967198) (40 . 0.0000000000) (41 . 0.0000000000) (42 . 0.4142135624) (91 . 0) (10 -30.9467273787 41.5712967198) (40 . 0.0000000000) (41 . 0.0000000000) (42 . 0.0000000000) (91 . 0) (10 -30.9467273787 36.9712967198) (40 . 0.0000000000) (41 . 0.0000000000) (42 . 0.4142135624) (91 . 0) (10 -30.4467273787 36.4712967198) (40 . 0.0000000000) (41 . 0.0000000000) (42 . 0.0000000000) (91 . 0) (10 -28.7152391243 36.4712967198) (40 . 0.0000000000) (41 . 0.0000000000) (42 . -0.2513806714) (91 . 0) (10 -28.4469016033 35.9712967198) (40 . 0.0000000000) (41 . 0.0000000000) (42 . 0.0000000000) (91 . 0) (10 -28.4469016033 35.7712967198) (40 . 0.0000000000) (41 . 0.0000000000) (42 . -0.4142135624) (91 . 0) (10 -29.0469016033 35.1712967198) (40 . 0.0000000000) (41 . 0.0000000000) (42 . 0.0000000000) (91 . 0) (10 -29.2469016033 35.1712967198) (40 . 0.0000000000) (41 . 0.0000000000) (42 . 0.4142135624) (91 . 0) (10 -29.6469016033 34.7712967198) (40 . 0.0000000000) (41 . 0.0000000000) (42 . 0.0000000000) (91 . 0) (10 -29.6469016033 34.5712967198) (40 . 0.0000000000) (41 . 0.0000000000) (42 . 0.4142135624) (91 . 0) (10 -29.2469016033 34.1712967198) (40 . 0.0000000000) (41 . 0.0000000000) (42 . 0.0000000000) (91 . 0) (10 -25.4469016033 34.1712967198) (40 . 0.0000000000) (41 . 0.0000000000) (42 . 0.4142225008) (91 . 0) (210 0.0000000000 0.0000000000 1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 -29.5017273787 37.5212967198) (40 . 0.0000000000) (41 . 0.0000000000) (42 . 0.0000000000) (91 . 0) (10 -29.5017273787 40.6212967198) (40 . 0.0000000000) (41 . 0.0000000000) (42 . 0.0000000000) (91 . 0) (10 -28.0017273787 40.6212967198) (40 . 0.0000000000) (41 . 0.0000000000) (42 . 0.0000000000) (91 . 0) (10 -28.0017273787 37.5212967198) (40 . 0.0000000000) (41 . 0.0000000000) (42 . 0.0000000000) (91 . 0) (210 0.0000000000 0.0000000000 1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 -26.6517273787 37.5212967198) (40 . 0.0000000000) (41 . 0.0000000000) (42 . 0.0000000000) (91 . 0) (10 -26.6517273787 40.6212967198) (40 . 0.0000000000) (41 . 0.0000000000) (42 . 0.0000000000) (91 . 0) (10 -25.1517273787 40.6212967198) (40 . 0.0000000000) (41 . 0.0000000000) (42 . 0.0000000000) (91 . 0) (10 -25.1517273787 37.5212967198) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 -32.8676567472 42.6610141281 0.0000000000) (11 -32.8676567472 37.8610141265 0.0000000000) (210 0.0000000000 0.0000000000 1.0000000000))
((0 . "ARC") (100 . "AcDbEntity") (67 . 0) (8 . "A-Window") (62 . 151) (6 . "Continuous") (100 . "AcDbCircle") (10 -957.1134354145 30.1339668118 0.0000000000) (40 . 10.7924013985) (210 0.0000000000 0.0000000000 -1.0000000000) (100 . "AcDbArc") (50 . -2.7631329826) (51 . -2.0079072900))
((0 . "LWPOLYLINE") (100 . "AcDbEntity") (67 . 0) (8 . "A-Window") (62 . 151) (6 . "Continuous") (100 . "AcDbPolyline") (90 . 27) (70 . 1) (43 . 0.0000000000) (38 . 0.0000000000) (39 . 0.0000000000) (10 -922.9545785754 -28.0404498570) (40 . 0.0000000000) (41 . 0.0000000000) (42 . 0.0000000000) (91 . 0) (10 -927.9386446589 -28.0469824966) (40 . 0.0000000000) (41 . 0.0000000000) (42 . 0.0000000000) (91 . 0) (10 -927.9386446589 -27.2238750999) (40 . 0.0000000000) (41 . 0.0000000000) (42 . -0.4142135624) (91 . 0) (10 -927.7386446591 -27.0238751000) (40 . 0.0000000000) (41 . 0.0000000000) (42 . 0.0000000000) (91 . 0) (10 -926.6596972281 -27.0238751000) (40 . 0.0000000000) (41 . 0.0000000000) (42 . 0.4142135624) (91 . 0) (10 -926.4596972282 -26.8238751001) (40 . 0.0000000000) (41 . 0.0000000000) (42 . 0.0000000000) (91 . 0) (10 -926.4596972282 -26.1211108948) (40 . 0.0000000000) (41 . 0.0000000000) (42 . 0.4142135624) (91 . 0) (10 -926.9596972279 -25.6211108950) (40 . 0.0000000000) (41 . 0.0000000000) (42 . 0.0000000000) (91 . 0) (10 -928.0493433886 -25.6211108950) (40 . 0.0000000000) (41 . 0.0000000000) (42 . -0.4142135624) (91 . 0) (10 -928.5493433883 -25.1211108953) (40 . 0.0000000000) (41 . 0.0000000000) (42 . 0.0000000000) (91 . 0) (10 -928.5493433883 -24.2222054634) (40 . 0.0000000000) (41 . 0.0000000000) (42 . -0.1452621195) (91 . 0) (10 -928.3330754330 -23.4935073420) (40 . 0.0000000000) (41 . 0.0000000000) (42 . -0.1071711367) (91 . 0) (10 -927.6077204277 -22.7755732682) (40 . 0.0000000000) (41 . 0.0000000000) (42 . -0.0774042911) (91 . 0) (10 -926.6176753725 -22.3426428514) (40 . 0.0000000000) (41 . 0.0000000000) (42 . -0.0645213706) (91 . 0) (10 -925.3344415057 -22.1763585931) (40 . 0.0000000000) (41 . 0.0000000000) (42 . -0.0645213706) (91 . 0) (10 -924.0512076389 -22.3426428514) (40 . 0.0000000000) (41 . 0.0000000000) (42 . -0.0774042911) (91 . 0) (10 -923.0611625837 -22.7755732682) (40 . 0.0000000000) (41 . 0.0000000000) (42 . -0.1071711367) (91 . 0) (10 -922.3358075785 -23.4935073420) (40 . 0.0000000000) (41 . 0.0000000000) (42 . -0.1452621195) (91 . 0) (10 -922.1195396232 -24.2222054634) (40 . 0.0000000000) (41 . 0.0000000000) (42 . 0.0000000000) (91 . 0) (10 -922.1195396232 -25.1211108953) (40 . 0.0000000000) (41 . 0.0000000000) (42 . -0.4142135624) (91 . 0) (10 -922.6195396229 -25.6211108950) (40 . 0.0000000000) (41 . 0.0000000000) (42 . 0.0000000000) (91 . 0) (10 -923.9596972297 -25.6211108950) (40 . 0.0000000000) (41 . 0.0000000000) (42 . 0.4142135624) (91 . 0) (10 -924.4596972294 -26.1211108948) (40 . 0.0000000000) (41 . 0.0000000000) (42 . 0.0000000000) (91 . 0) (10 -924.4596972294 -26.8238751001) (40 . 0.0000000000) (41 . 0.0000000000) (42 . 0.4142135624) (91 . 0) (10 -924.2596972295 -27.0238751000) (40 . 0.0000000000) (41 . 0.0000000000) (42 . 0.0000000000) (91 . 0) (10 -923.1545785753 -27.0238751000) (40 . 0.0000000000) (41 . 0.0000000000) (42 . -0.4142135624) (91 . 0) (10 -922.9545785754 -27.2238750999) (40 . 0.0000000000) (41 . 0.0000000000) (42 . 0.0000000000) (91 . 0) (210 0.0000000000 0.0000000000 -1.0000000000))
((0 . "LWPOLYLINE") (100 . "AcDbEntity") (67 . 0) (8 . "A-Window") (62 . 151) (6 . "Continuous") (370 . -3) (100 . "AcDbPolyline") (90 . 21) (70 . 1) (43 . 0.0000000000) (38 . 0.0000000000) (39 . 0.0000000000) (10 -922.6195396228 -24.2222054634) (40 . 0.0000000000) (41 . 0.0000000000) (42 . 0.1452621195) (91 . 0) (10 -922.7548556364 -23.7662686384) (40 . 0.0000000000) (41 . 0.0000000000) (42 . 0.1071711367) (91 . 0) (10 -923.3296003500 -23.1974039988) (40 . 0.0000000000) (41 . 0.0000000000) (42 . 0.0774042911) (91 . 0) (10 -924.1786498795 -22.8261286061) (40 . 0.0000000000) (41 . 0.0000000000) (42 . 0.0645213706) (91 . 0) (10 -925.3344415057 -22.6763585928) (40 . 0.0000000000) (41 . 0.0000000000) (42 . 0.0645213706) (91 . 0) (10 -926.4902331319 -22.8261286061) (40 . 0.0000000000) (41 . 0.0000000000) (42 . 0.0774042911) (91 . 0) (10 -927.3392826615 -23.1974039988) (40 . 0.0000000000) (41 . 0.0000000000) (42 . 0.1071711367) (91 . 0) (10 -927.9140273750 -23.7662686384) (40 . 0.0000000000) (41 . 0.0000000000) (42 . 0.1452621195) (91 . 0) (10 -928.0493433886 -24.2222054634) (40 . 0.0000000000) (41 . 0.0000000000) (42 . 0.0000000000) (91 . 0) (10 -928.0493433886 -24.6238751015) (40 . 0.0000000000) (41 . 0.0000000000) (42 . 0.4142135624) (91 . 0) (10 -927.5493433889 -25.1238751012) (40 . 0.0000000000) (41 . 0.0000000000) (42 . 0.0000000000) (91 . 0) (10 -926.3009876182 -25.1238751012) (40 . 0.0000000000) (41 . 0.0000000000) (42 . -0.3939487093) (91 . 0) (10 -925.8022009802 -25.5890628983) (40 . 0.0000000000) (41 . 0.0000000000) (42 . 0.0000000000) (91 . 0) (10 -925.7150469044 -26.8377999812) (40 . 0.0000000000) (41 . 0.0000000000) (42 . 0.3939487093) (91 . 0) (10 -925.5155322493 -27.0238751000) (40 . 0.0000000000) (41 . 0.0000000000) (42 . 0.0000000000) (91 . 0) (10 -925.3868710308 -27.0238751000) (40 . 0.0000000000) (41 . 0.0000000000) (42 . 0.3852515762) (91 . 0) (10 -925.1878678957 -26.8438188249) (40 . 0.0000000000) (41 . 0.0000000000) (42 . 0.0000000000) (91 . 0) (10 -925.0606105924 -25.5740157889) (40 . 0.0000000000) (41 . 0.0000000000) (42 . -0.3852515762) (91 . 0) (10 -924.5631027545 -25.1238751012) (40 . 0.0000000000) (41 . 0.0000000000) (42 . 0.0000000000) (91 . 0) (10 -923.1195396226 -25.1238751012) (40 . 0.0000000000) (41 . 0.0000000000) (42 . 0.4142135624) (91 . 0) (10 -922.6195396228 -24.6238751015) (40 . 0.0000000000) (41 . 0.0000000000) (42 . 0.0000000000) (91 . 0) (210 0.0000000000 0.0000000000 -1.0000000000))
((0 . "ARC") (100 . "AcDbEntity") (67 . 0) (8 . "A-Window") (62 . 151) (6 . "Continuous") (100 . "AcDbCircle") (10 -42.1707869059 30.1330273349 0.0000000000) (40 . 10.7924013985) (210 0.0000000000 0.0000000000 -1.0000000000) (100 . "AcDbArc") (50 . -1.1336853636) (51 . -0.3784596710))
((0 . "LWPOLYLINE") (100 . "AcDbEntity") (67 . 0) (8 . "A-Window") (62 . 151) (6 . "Continuous") (100 . "AcDbPolyline") (90 . 27) (70 . 1) (43 . 0.0000000000) (38 . 0.0000000000) (39 . 0.0000000000) (10 -71.3455776614 -28.0404498568) (40 . 0.0000000000) (41 . 0.0000000000) (42 . 0.0000000000) (91 . 0) (10 -76.3296437449 -28.0469824964) (40 . 0.0000000000) (41 . 0.0000000000) (42 . 0.0000000000) (91 . 0) (10 -76.3296437449 -27.2238750997) (40 . 0.0000000000) (41 . 0.0000000000) (42 . -0.4142135624) (91 . 0) (10 -76.1296437451 -27.0238750998) (40 . 0.0000000000) (41 . 0.0000000000) (42 . 0.0000000000) (91 . 0) (10 -75.0506963141 -27.0238750998) (40 . 0.0000000000) (41 . 0.0000000000) (42 . 0.4142135624) (91 . 0) (10 -74.8506963142 -26.8238750999) (40 . 0.0000000000) (41 . 0.0000000000) (42 . 0.0000000000) (91 . 0) (10 -74.8506963142 -26.1211108946) (40 . 0.0000000000) (41 . 0.0000000000) (42 . 0.4142135624) (91 . 0) (10 -75.3506963139 -25.6211108949) (40 . 0.0000000000) (41 . 0.0000000000) (42 . 0.0000000000) (91 . 0) (10 -76.4403424746 -25.6211108949) (40 . 0.0000000000) (41 . 0.0000000000) (42 . -0.4142135624) (91 . 0) (10 -76.9403424743 -25.1211108951) (40 . 0.0000000000) (41 . 0.0000000000) (42 . 0.0000000000) (91 . 0) (10 -76.9403424743 -24.2222054632) (40 . 0.0000000000) (41 . 0.0000000000) (42 . -0.1452621195) (91 . 0) (10 -76.7240745190 -23.4935073418) (40 . 0.0000000000) (41 . 0.0000000000) (42 . -0.1071711367) (91 . 0) (10 -75.9987195137 -22.7755732680) (40 . 0.0000000000) (41 . 0.0000000000) (42 . -0.0774042911) (91 . 0) (10 -75.0086744585 -22.3426428513) (40 . 0.0000000000) (41 . 0.0000000000) (42 . -0.0645213706) (91 . 0) (10 -73.7254405917 -22.1763585929) (40 . 0.0000000000) (41 . 0.0000000000) (42 . -0.0645213706) (91 . 0) (10 -72.4422067249 -22.3426428513) (40 . 0.0000000000) (41 . 0.0000000000) (42 . -0.0774042911) (91 . 0) (10 -71.4521616697 -22.7755732680) (40 . 0.0000000000) (41 . 0.0000000000) (42 . -0.1071711367) (91 . 0) (10 -70.7268066644 -23.4935073418) (40 . 0.0000000000) (41 . 0.0000000000) (42 . -0.1452621195) (91 . 0) (10 -70.5105387091 -24.2222054632) (40 . 0.0000000000) (41 . 0.0000000000) (42 . 0.0000000000) (91 . 0) (10 -70.5105387091 -25.1211108951) (40 . 0.0000000000) (41 . 0.0000000000) (42 . -0.4142135624) (91 . 0) (10 -71.0105387089 -25.6211108949) (40 . 0.0000000000) (41 . 0.0000000000) (42 . 0.0000000000) (91 . 0) (10 -72.3506963157 -25.6211108949) (40 . 0.0000000000) (41 . 0.0000000000) (42 . 0.4142135624) (91 . 0) (10 -72.8506963154 -26.1211108946) (40 . 0.0000000000) (41 . 0.0000000000) (42 . 0.0000000000) (91 . 0) (10 -72.8506963154 -26.8238750999) (40 . 0.0000000000) (41 . 0.0000000000) (42 . 0.4142135624) (91 . 0) (10 -72.6506963155 -27.0238750998) (40 . 0.0000000000) (41 . 0.0000000000) (42 . 0.0000000000) (91 . 0) (10 -71.5455776613 -27.0238750998) (40 . 0.0000000000) (41 . 0.0000000000) (42 . -0.4142135624) (91 . 0) (10 -71.3455776614 -27.2238750997) (40 . 0.0000000000) (41 . 0.0000000000) (42 . 0.0000000000) (91 . 0) (210 0.0000000000 0.0000000000 -1.0000000000))
((0 . "LWPOLYLINE") (100 . "AcDbEntity") (67 . 0) (8 . "A-Window") (62 . 151) (6 . "Continuous") (370 . -3) (100 . "AcDbPolyline") (90 . 21) (70 . 1) (43 . 0.0000000000) (38 . 0.0000000000) (39 . 0.0000000000) (10 -71.0105387088 -24.2222054632) (40 . 0.0000000000) (41 . 0.0000000000) (42 . 0.1452621195) (91 . 0) (10 -71.1458547224 -23.7662686382) (40 . 0.0000000000) (41 . 0.0000000000) (42 . 0.1071711367) (91 . 0) (10 -71.7205994359 -23.1974039986) (40 . 0.0000000000) (41 . 0.0000000000) (42 . 0.0774042911) (91 . 0) (10 -72.5696489655 -22.8261286059) (40 . 0.0000000000) (41 . 0.0000000000) (42 . 0.0645213706) (91 . 0) (10 -73.7254405917 -22.6763585926) (40 . 0.0000000000) (41 . 0.0000000000) (42 . 0.0645213706) (91 . 0) (10 -74.8812322179 -22.8261286059) (40 . 0.0000000000) (41 . 0.0000000000) (42 . 0.0774042911) (91 . 0) (10 -75.7302817475 -23.1974039986) (40 . 0.0000000000) (41 . 0.0000000000) (42 . 0.1071711367) (91 . 0) (10 -76.3050264610 -23.7662686382) (40 . 0.0000000000) (41 . 0.0000000000) (42 . 0.1452621195) (91 . 0) (10 -76.4403424746 -24.2222054632) (40 . 0.0000000000) (41 . 0.0000000000) (42 . 0.0000000000) (91 . 0) (10 -76.4403424746 -24.6238751013) (40 . 0.0000000000) (41 . 0.0000000000) (42 . 0.4142135624) (91 . 0) (10 -75.9403424749 -25.1238751011) (40 . 0.0000000000) (41 . 0.0000000000) (42 . 0.0000000000) (91 . 0) (10 -74.6919867042 -25.1238751011) (40 . 0.0000000000) (41 . 0.0000000000) (42 . -0.3939487093) (91 . 0) (10 -74.1932000662 -25.5890628981) (40 . 0.0000000000) (41 . 0.0000000000) (42 . 0.0000000000) (91 . 0) (10 -74.1060459904 -26.8377999810) (40 . 0.0000000000) (41 . 0.0000000000) (42 . 0.3939487093) (91 . 0) (10 -73.9065313352 -27.0238750998) (40 . 0.0000000000) (41 . 0.0000000000) (42 . 0.0000000000) (91 . 0) (10 -73.7778701168 -27.0238750998) (40 . 0.0000000000) (41 . 0.0000000000) (42 . 0.3852515762) (91 . 0) (10 -73.5788669816 -26.8438188247) (40 . 0.0000000000) (41 . 0.0000000000) (42 . 0.0000000000) (91 . 0) (10 -73.4516096783 -25.5740157887) (40 . 0.0000000000) (41 . 0.0000000000) (42 . -0.3852515762) (91 . 0) (10 -72.9541018405 -25.1238751011) (40 . 0.0000000000) (41 . 0.0000000000) (42 . 0.0000000000) (91 . 0) (10 -71.5105387085 -25.1238751011) (40 . 0.0000000000) (41 . 0.0000000000) (42 . 0.4142135624) (91 . 0) (10 -71.0105387088 -24.6238751013) (40 . 0.0000000000) (41 . 0.0000000000) (42 . 0.0000000000) (91 . 0) (210 0.0000000000 0.0000000000 -1.0000000000))
((0 . "ARC") (100 . "AcDbEntity") (67 . 0) (8 . "A-Window") (62 . 3) (6 . "Continuous") (100 . "AcDbCircle") (10 35.9548458940 -35.8672071369 0.0000000000) (40 . 6.2864202362) (210 0.0000000000 0.0000000000 1.0000000000) (100 . "AcDbArc") (50 . 1.4291834929) (51 . 2.2224516076))
((0 . "ARC") (100 . "AcDbEntity") (67 . 0) (8 . "A-Window") (62 . 3) (6 . "Continuous") (100 . "AcDbCircle") (10 -963.3293764264 -35.8672071371 0.0000000000) (40 . 6.2864202362) (210 0.0000000000 0.0000000000 -1.0000000000) (100 . "AcDbArc") (50 . 1.4291834929) (51 . 2.2224516076))
((0 . "LINE") (100 . "AcDbEntity") (67 . 0) (8 . "A-Window") (62 . 7) (6 . "Continuous") (100 . "AcDbLine") (10 48.6421120915 5.8555364404 0.0000000000) (11 48.6421120915 5.8410358252 0.0000000000) (210 0.0000000000 0.0000000000 1.0000000000))
((0 . "LINE") (100 . "AcDbEntity") (67 . 0) (8 . "A-Window") (62 . 7) (6 . "Continuous") (100 . "AcDbLine") (10 46.6421120915 5.8555364404 0.0000000000) (11 46.6421120915 5.8410358252 0.0000000000) (210 0.0000000000 0.0000000000 1.0000000000))
((0 . "LINE") (100 . "AcDbEntity") (67 . 0) (8 . "A-Window") (62 . 7) (6 . "Continuous") (100 . "AcDbLine") (10 48.6421120915 -2.1444635596 0.0000000000) (11 51.6421120915 -2.1444635596 0.0000000000) (210 0.0000000000 0.0000000000 1.0000000000))
((0 . "LINE") (100 . "AcDbEntity") (67 . 0) (8 . "A-Window") (62 . 7) (6 . "Continuous") (100 . "AcDbLine") (10 48.6421120915 -2.1444635596 0.0000000000) (11 48.6421120915 5.8410358252 0.0000000000) (210 0.0000000000 0.0000000000 1.0000000000))
((0 . "LINE") (100 . "AcDbEntity") (67 . 0) (8 . "A-Window") (62 . 7) (6 . "Continuous") (100 . "AcDbLine") (10 46.6421120915 -2.1444635596 0.0000000000) (11 48.6421120915 -2.1444635596 0.0000000000) (210 0.0000000000 0.0000000000 1.0000000000))
((0 . "LINE") (100 . "AcDbEntity") (67 . 0) (8 . "A-Window") (62 . 7) (6 . "Continuous") (100 . "AcDbLine") (10 46.6421120915 5.8410358252 0.0000000000) (11 46.6421120915 -2.1444635596 0.0000000000) (210 0.0000000000 0.0000000000 1.0000000000))
((0 . "LINE") (100 . "AcDbEntity") (67 . 0) (8 . "A-Window") (62 . 7) (6 . "Continuous") (100 . "AcDbLine") (10 48.6421120915 13.8526430410 0.0000000000) (11 51.6421120915 13.8526430410 0.0000000000) (210 0.0000000000 0.0000000000 1.0000000000))
((0 . "LINE") (100 . "AcDbEntity") (67 . 0) (8 . "A-Window") (62 . 7) (6 . "Continuous") (100 . "AcDbLine") (10 46.6421120915 13.8526430410 0.0000000000) (11 46.6421120915 5.8555364404 0.0000000000) (210 0.0000000000 0.0000000000 1.0000000000))
((0 . "LINE") (100 . "AcDbEntity") (67 . 0) (8 . "A-Window") (62 . 7) (6 . "Continuous") (100 . "AcDbLine") (10 48.6421120915 13.8526430410 0.0000000000) (11 46.6421120915 13.8526430410 0.0000000000) (210 0.0000000000 0.0000000000 1.0000000000))
((0 . "LINE") (100 . "AcDbEntity") (67 . 0) (8 . "A-Window") (62 . 7) (6 . "Continuous") (100 . "AcDbLine") (10 48.6421120915 5.8555364404 0.0000000000) (11 48.6421120915 13.8526430410 0.0000000000) (210 0.0000000000 0.0000000000 1.0000000000))
((0 . "LINE") (100 . "AcDbEntity") (67 . 0) (8 . "A-Window") (62 . 7) (6 . "Continuous") (100 . "AcDbLine") (10 57.9421120915 18.8526430410 0.0000000000) (11 57.8421120915 18.8526430410 0.0000000000) (210 0.0000000000 0.0000000000 1.0000000000))
((0 . "LINE") (100 . "AcDbEntity") (67 . 0) (8 . "A-Window") (62 . 7) (6 . "Continuous") (100 . "AcDbLine") (10 57.9421120915 15.9026430410 0.0000000000) (11 57.9421120915 18.8526430410 0.0000000000) (210 0.0000000000 0.0000000000 1.0000000000))
((0 . "LINE") (100 . "AcDbEntity") (67 . 0) (8 . "A-Window") (62 . 7) (6 . "Continuous") (100 . "AcDbLine") (10 58.8421120915 15.6026430410 0.0000000000) (11 58.2421120915 15.6026430410 0.0000000000) (210 0.0000000000 0.0000000000 1.0000000000))
((0 . "LINE") (100 . "AcDbEntity") (67 . 0) (8 . "A-Window") (62 . 7) (6 . "Continuous") (100 . "AcDbLine") (10 59.1421120915 -3.5973569590 0.0000000000) (11 59.1421120915 -2.1444635596 0.0000000000) (210 0.0000000000 0.0000000000 1.0000000000))
((0 . "LINE") (100 . "AcDbEntity") (67 . 0) (8 . "A-Window") (62 . 7) (6 . "Continuous") (100 . "AcDbLine") (10 59.1421120915 13.8526430410 0.0000000000) (11 59.1421120915 15.3026430410 0.0000000000) (210 0.0000000000 0.0000000000 1.0000000000))
((0 . "LINE") (100 . "AcDbEntity") (67 . 0) (8 . "A-Window") (62 . 7) (6 . "Continuous") (100 . "AcDbLine") (10 58.2421120915 -3.8973569590 0.0000000000) (11 58.8421120915 -3.8973569590 0.0000000000) (210 0.0000000000 0.0000000000 1.0000000000))
((0 . "LINE") (100 . "AcDbEntity") (67 . 0) (8 . "A-Window") (62 . 7) (6 . "Continuous") (100 . "AcDbLine") (10 57.9421120915 -7.1473569590 0.0000000000) (11 57.9421120915 -4.1973569590 0.0000000000) (210 0.0000000000 0.0000000000 1.0000000000))
((0 . "LINE") (100 . "AcDbEntity") (67 . 0) (8 . "A-Window") (62 . 7) (6 . "Continuous") (100 . "AcDbLine") (10 57.8421120915 -7.1473569590 0.0000000000) (11 57.9421120915 -7.1473569590 0.0000000000) (210 0.0000000000 0.0000000000 1.0000000000))
((0 . "LINE") (100 . "AcDbEntity") (67 . 0) (8 . "A-Window") (62 . 7) (6 . "Continuous") (100 . "AcDbLine") (10 53.6421120915 -3.2473569590 0.0000000000) (11 53.6421120915 -5.8473569590 0.0000000000) (210 0.0000000000 0.0000000000 1.0000000000))
((0 . "LINE") (100 . "AcDbEntity") (67 . 0) (8 . "A-Window") (62 . 7) (6 . "Continuous") (100 . "AcDbLine") (10 56.8421120915 15.3526430410 0.0000000000) (11 57.8421120915 15.3526430410 0.0000000000) (210 0.0000000000 0.0000000000 1.0000000000))
((0 . "LINE") (100 . "AcDbEntity") (67 . 0) (8 . "A-Window") (62 . 7) (6 . "Continuous") (100 . "AcDbLine") (10 56.8421120915 -3.6473569590 0.0000000000) (11 57.8421120915 -3.6473569590 0.0000000000) (210 0.0000000000 0.0000000000 1.0000000000))
((0 . "LINE") (100 . "AcDbEntity") (67 . 0) (8 . "A-Window") (62 . 7) (6 . "Continuous") (100 . "AcDbLine") (10 53.3421120915 14.6526430410 0.0000000000) (11 52.6421120915 14.6526430410 0.0000000000) (210 0.0000000000 0.0000000000 1.0000000000))
((0 . "LINE") (100 . "AcDbEntity") (67 . 0) (8 . "A-Window") (62 . 7) (6 . "Continuous") (100 . "AcDbLine") (10 52.6421120915 14.6526430410 0.0000000000) (11 52.6421120915 18.8526430410 0.0000000000) (210 0.0000000000 0.0000000000 1.0000000000))
((0 . "LINE") (100 . "AcDbEntity") (67 . 0) (8 . "A-Window") (62 . 7) (6 . "Continuous") (100 . "AcDbLine") (10 53.6421120915 17.5526430410 0.0000000000) (11 53.6421120915 14.9526430410 0.0000000000) (210 0.0000000000 0.0000000000 1.0000000000))
((0 . "LINE") (100 . "AcDbEntity") (67 . 0) (8 . "A-Window") (62 . 7) (6 . "Continuous") (100 . "AcDbLine") (10 53.9421120915 -6.1473569590 0.0000000000) (11 56.5421120915 -6.1473569590 0.0000000000) (210 0.0000000000 0.0000000000 1.0000000000))
((0 . "LINE") (100 . "AcDbEntity") (67 . 0) (8 . "A-Window") (62 . 7) (6 . "Continuous") (100 . "AcDbLine") (10 52.6421120915 18.8526430410 0.0000000000) (11 57.8421120915 18.8526430410 0.0000000000) (210 0.0000000000 0.0000000000 1.0000000000))
((0 . "LINE") (100 . "AcDbEntity") (67 . 0) (8 . "A-Window") (62 . 7) (6 . "Continuous") (100 . "AcDbLine") (10 57.8421120915 -7.1473569590 0.0000000000) (11 52.6421120915 -7.1473569590 0.0000000000) (210 0.0000000000 0.0000000000 1.0000000000))
((0 . "LINE") (100 . "AcDbEntity") (67 . 0) (8 . "A-Window") (62 . 7) (6 . "Continuous") (100 . "AcDbLine") (10 52.6421120915 -7.1473569590 0.0000000000) (11 52.6421120915 -2.9473569590 0.0000000000) (210 0.0000000000 0.0000000000 1.0000000000))
((0 . "LINE") (100 . "AcDbEntity") (67 . 0) (8 . "A-Window") (62 . 7) (6 . "Continuous") (100 . "AcDbLine") (10 52.6421120915 -2.9473569590 0.0000000000) (11 53.3421120915 -2.9473569590 0.0000000000) (210 0.0000000000 0.0000000000 1.0000000000))
((0 . "LINE") (100 . "AcDbEntity") (67 . 0) (8 . "A-Window") (62 . 7) (6 . "Continuous") (100 . "AcDbLine") (10 56.8421120915 -3.6473569590 0.0000000000) (11 56.8421120915 15.3526430410 0.0000000000) (210 0.0000000000 0.0000000000 1.0000000000))
((0 . "LINE") (100 . "AcDbEntity") (67 . 0) (8 . "A-Window") (62 . 7) (6 . "Continuous") (100 . "AcDbLine") (10 56.8421120915 -5.8473569590 0.0000000000) (11 56.8421120915 -3.6473569590 0.0000000000) (210 0.0000000000 0.0000000000 1.0000000000))
((0 . "LINE") (100 . "AcDbEntity") (67 . 0) (8 . "A-Window") (62 . 7) (6 . "Continuous") (100 . "AcDbLine") (10 56.8421120915 15.3526430410 0.0000000000) (11 56.8421120915 17.5526430410 0.0000000000) (210 0.0000000000 0.0000000000 1.0000000000))
((0 . "LINE") (100 . "AcDbEntity") (67 . 0) (8 . "A-Window") (62 . 7) (6 . "Continuous") (100 . "AcDbLine") (10 56.5421120915 17.8526430410 0.0000000000) (11 53.9421120915 17.8526430410 0.0000000000) (210 0.0000000000 0.0000000000 1.0000000000))
((0 . "LINE") (100 . "AcDbEntity") (67 . 0) (8 . "A-Window") (62 . 7) (6 . "Continuous") (100 . "AcDbLine") (10 57.8421120915 15.3526430410 0.0000000000) (11 57.8421120915 13.8526430410 0.0000000000) (210 0.0000000000 0.0000000000 1.0000000000))
((0 . "LINE") (100 . "AcDbEntity") (67 . 0) (8 . "A-Window") (62 . 7) (6 . "Continuous") (100 . "AcDbLine") (10 57.8421120915 12.5010701566 0.0000000000) (11 57.8421120915 -0.7957840745 0.0000000000) (210 0.0000000000 0.0000000000 1.0000000000))
((0 . "LINE") (100 . "AcDbEntity") (67 . 0) (8 . "A-Window") (62 . 7) (6 . "Continuous") (100 . "AcDbLine") (10 57.8421120915 -2.1444635596 0.0000000000) (11 57.8421120915 -3.6473569590 0.0000000000) (210 0.0000000000 0.0000000000 1.0000000000))
((0 . "LINE") (100 . "AcDbEntity") (67 . 0) (8 . "A-Window") (62 . 7) (6 . "Continuous") (100 . "AcDbLine") (10 57.8421120915 18.8526430410 0.0000000000) (11 57.8421120915 15.3526430410 0.0000000000) (210 0.0000000000 0.0000000000 1.0000000000))
((0 . "LINE") (100 . "AcDbEntity") (67 . 0) (8 . "A-Window") (62 . 7) (6 . "Continuous") (100 . "AcDbLine") (10 57.8421120915 -3.6473569590 0.0000000000) (11 57.8421120915 -7.1473569590 0.0000000000) (210 0.0000000000 0.0000000000 1.0000000000))
((0 . "LINE") (100 . "AcDbEntity") (67 . 0) (8 . "A-Window") (62 . 7) (6 . "Continuous") (100 . "AcDbLine") (10 51.6421120915 19.8026430410 0.0000000000) (11 51.6421120915 -8.0973569590 0.0000000000) (210 0.0000000000 0.0000000000 1.0000000000))
((0 . "LINE") (100 . "AcDbEntity") (67 . 0) (8 . "A-Window") (62 . 7) (6 . "Continuous") (100 . "AcDbLine") (10 52.6421120915 19.1026430410 0.0000000000) (11 58.0421120915 19.1026430410 0.0000000000) (210 0.0000000000 0.0000000000 1.0000000000))
((0 . "LINE") (100 . "AcDbEntity") (67 . 0) (8 . "A-Window") (62 . 7) (6 . "Continuous") (100 . "AcDbLine") (10 52.6421120915 -7.3973569590 0.0000000000) (11 52.6421120915 -7.1473569590 0.0000000000) (210 0.0000000000 0.0000000000 1.0000000000))
((0 . "LINE") (100 . "AcDbEntity") (67 . 0) (8 . "A-Window") (62 . 7) (6 . "Continuous") (100 . "AcDbLine") (10 52.6421120915 -2.9473569590 0.0000000000) (11 52.6421120915 14.6526430410 0.0000000000) (210 0.0000000000 0.0000000000 1.0000000000))
((0 . "LINE") (100 . "AcDbEntity") (67 . 0) (8 . "A-Window") (62 . 7) (6 . "Continuous") (100 . "AcDbLine") (10 52.6421120915 18.8526430410 0.0000000000) (11 52.6421120915 19.1026430410 0.0000000000) (210 0.0000000000 0.0000000000 1.0000000000))
((0 . "LINE") (100 . "AcDbEntity") (67 . 0) (8 . "A-Window") (62 . 7) (6 . "Continuous") (100 . "AcDbLine") (10 51.9421120915 -8.3973569590 0.0000000000) (11 59.0421120915 -8.3973569590 0.0000000000) (210 0.0000000000 0.0000000000 1.0000000000))
((0 . "LINE") (100 . "AcDbEntity") (67 . 0) (8 . "A-Window") (62 . 7) (6 . "Continuous") (100 . "AcDbLine") (10 59.0421120915 20.1026430410 0.0000000000) (11 51.9421120915 20.1026430410 0.0000000000) (210 0.0000000000 0.0000000000 1.0000000000))
((0 . "LINE") (100 . "AcDbEntity") (67 . 0) (8 . "A-Window") (62 . 7) (6 . "Continuous") (100 . "AcDbLine") (10 59.3421120915 16.2026430410 0.0000000000) (11 59.3421120915 19.8026430410 0.0000000000) (210 0.0000000000 0.0000000000 1.0000000000))
((0 . "LINE") (100 . "AcDbEntity") (67 . 0) (8 . "A-Window") (62 . 7) (6 . "Continuous") (100 . "AcDbLine") (10 58.0421120915 -7.3973569590 0.0000000000) (11 52.6421120915 -7.3973569590 0.0000000000) (210 0.0000000000 0.0000000000 1.0000000000))
((0 . "LINE") (100 . "AcDbEntity") (67 . 0) (8 . "A-Window") (62 . 7) (6 . "Continuous") (100 . "AcDbLine") (10 58.3421120915 -4.4973569590 0.0000000000) (11 58.3421120915 -7.0973569590 0.0000000000) (210 0.0000000000 0.0000000000 1.0000000000))
((0 . "LINE") (100 . "AcDbEntity") (67 . 0) (8 . "A-Window") (62 . 7) (6 . "Continuous") (100 . "AcDbLine") (10 59.3421120915 -8.0973569590 0.0000000000) (11 59.3421120915 -4.4973569590 0.0000000000) (210 0.0000000000 0.0000000000 1.0000000000))
((0 . "LINE") (100 . "AcDbEntity") (67 . 0) (8 . "A-Window") (62 . 7) (6 . "Continuous") (100 . "AcDbLine") (10 59.0421120915 -4.1973569590 0.0000000000) (11 58.6421120915 -4.1973569590 0.0000000000) (210 0.0000000000 0.0000000000 1.0000000000))
((0 . "LINE") (100 . "AcDbEntity") (67 . 0) (8 . "A-Window") (62 . 7) (6 . "Continuous") (100 . "AcDbLine") (10 58.3421120915 18.8026430410 0.0000000000) (11 58.3421120915 16.2026430410 0.0000000000) (210 0.0000000000 0.0000000000 1.0000000000))
((0 . "LINE") (100 . "AcDbEntity") (67 . 0) (8 . "A-Window") (62 . 7) (6 . "Continuous") (100 . "AcDbLine") (10 58.6421120915 15.9026430410 0.0000000000) (11 59.0421120915 15.9026430410 0.0000000000) (210 0.0000000000 0.0000000000 1.0000000000))
((0 . "LINE") (100 . "AcDbEntity") (67 . 0) (8 . "A-Window") (62 . 7) (6 . "Continuous") (100 . "AcDbLine") (10 58.4421120915 -2.1473569590 0.0000000000) (11 58.4421120915 -2.1444635596 0.0000000000) (210 0.0000000000 0.0000000000 1.0000000000))
((0 . "LINE") (100 . "AcDbEntity") (67 . 0) (8 . "A-Window") (62 . 7) (6 . "Continuous") (100 . "AcDbLine") (10 57.8421120915 -2.1473569590 0.0000000000) (11 58.4421120915 -2.1473569590 0.0000000000) (210 0.0000000000 0.0000000000 1.0000000000))
((0 . "LINE") (100 . "AcDbEntity") (67 . 0) (8 . "A-Window") (62 . 7) (6 . "Continuous") (100 . "AcDbLine") (10 57.8421120915 13.8526430410 0.0000000000) (11 57.8421120915 12.5010701566 0.0000000000) (210 0.0000000000 0.0000000000 1.0000000000))
((0 . "LINE") (100 . "AcDbEntity") (67 . 0) (8 . "A-Window") (62 . 7) (6 . "Continuous") (100 . "AcDbLine") (10 57.8421120915 -0.7957840745 0.0000000000) (11 57.8421120915 -2.1444635596 0.0000000000) (210 0.0000000000 0.0000000000 1.0000000000))
((0 . "LINE") (100 . "AcDbEntity") (67 . 0) (8 . "A-Window") (62 . 7) (6 . "Continuous") (100 . "AcDbLine") (10 63.6421120901 5.8555364403 0.0000000000) (11 63.6421120901 5.8410358253 0.0000000000) (210 0.0000000000 0.0000000000 1.0000000000))
((0 . "LINE") (100 . "AcDbEntity") (67 . 0) (8 . "A-Window") (62 . 7) (6 . "Continuous") (100 . "AcDbLine") (10 61.6421120901 5.8555364403 0.0000000000) (11 61.6421120901 5.8410358253 0.0000000000) (210 0.0000000000 0.0000000000 1.0000000000))
((0 . "LINE") (100 . "AcDbEntity") (67 . 0) (8 . "A-Window") (62 . 7) (6 . "Continuous") (100 . "AcDbLine") (10 57.8421120915 -2.1444635596 0.0000000000) (11 61.6421120901 -2.1444635596 0.0000000000) (210 0.0000000000 0.0000000000 1.0000000000))
((0 . "LINE") (100 . "AcDbEntity") (67 . 0) (8 . "A-Window") (62 . 7) (6 . "Continuous") (100 . "AcDbLine") (10 63.6421120901 5.8555364403 0.0000000000) (11 63.6421120901 13.8526430410 0.0000000000) (210 0.0000000000 0.0000000000 1.0000000000))
((0 . "LINE") (100 . "AcDbEntity") (67 . 0) (8 . "A-Window") (62 . 7) (6 . "Continuous") (100 . "AcDbLine") (10 61.6421120901 13.8526430410 0.0000000000) (11 61.6421120901 5.8555364403 0.0000000000) (210 0.0000000000 0.0000000000 1.0000000000))
((0 . "LINE") (100 . "AcDbEntity") (67 . 0) (8 . "A-Window") (62 . 7) (6 . "Continuous") (100 . "AcDbLine") (10 61.6421120901 5.8410358253 0.0000000000) (11 61.6421120901 -2.1444635596 0.0000000000) (210 0.0000000000 0.0000000000 1.0000000000))
((0 . "LINE") (100 . "AcDbEntity") (67 . 0) (8 . "A-Window") (62 . 7) (6 . "Continuous") (100 . "AcDbLine") (10 63.6421120901 -2.1444635596 0.0000000000) (11 63.6421120901 5.8410358253 0.0000000000) (210 0.0000000000 0.0000000000 1.0000000000))
((0 . "LINE") (100 . "AcDbEntity") (67 . 0) (8 . "A-Window") (62 . 7) (6 . "Continuous") (100 . "AcDbLine") (10 61.6421120901 -2.1444635596 0.0000000000) (11 63.6421120901 -2.1444635596 0.0000000000) (210 0.0000000000 0.0000000000 1.0000000000))
((0 . "LINE") (100 . "AcDbEntity") (67 . 0) (8 . "A-Window") (62 . 7) (6 . "Continuous") (100 . "AcDbLine") (10 61.6421120901 13.8526430410 0.0000000000) (11 63.6421120901 13.8526430410 0.0000000000) (210 0.0000000000 0.0000000000 1.0000000000))
((0 . "LINE") (100 . "AcDbEntity") (67 . 0) (8 . "A-Window") (62 . 7) (6 . "Continuous") (100 . "AcDbLine") (10 57.8421120915 13.8526430410 0.0000000000) (11 61.6421120901 13.8526430410 0.0000000000) (210 0.0000000000 0.0000000000 1.0000000000))
((0 . "LINE") (100 . "AcDbEntity") (67 . 0) (8 . "A-Window") (62 . 7) (6 . "Continuous") (100 . "AcDbLine") (10 56.8421120915 10.2026430410 0.0000000000) (11 56.6421120915 10.2026430410 0.0000000000) (210 0.0000000000 0.0000000000 1.0000000000))
((0 . "LINE") (100 . "AcDbEntity") (67 . 0) (8 . "A-Window") (62 . 7) (6 . "Continuous") (100 . "AcDbLine") (10 56.8421120915 1.5026430410 0.0000000000) (11 56.6421120915 1.5026430410 0.0000000000) (210 0.0000000000 0.0000000000 1.0000000000))
((0 . "LINE") (100 . "AcDbEntity") (67 . 0) (8 . "A-Window") (62 . 7) (6 . "Continuous") (100 . "AcDbLine") (10 55.5921120915 2.5526430410 0.0000000000) (11 55.5921120915 9.1526430410 0.0000000000) (210 0.0000000000 0.0000000000 1.0000000000))
((0 . "ARC") (100 . "AcDbEntity") (67 . 0) (8 . "A-Window") (62 . 7) (6 . "Continuous") (100 . "AcDbCircle") (10 56.6421120915 2.5526430410 0.0000000000) (40 . 1.0500000000) (210 0.0000000000 0.0000000000 1.0000000000) (100 . "AcDbArc") (50 . -3.1415926536) (51 . -1.5707963268))
((0 . "ARC") (100 . "AcDbEntity") (67 . 0) (8 . "A-Window") (62 . 7) (6 . "Continuous") (100 . "AcDbCircle") (10 56.6421120915 9.1526430410 0.0000000000) (40 . 1.0500000000) (210 0.0000000000 0.0000000000 1.0000000000) (100 . "AcDbArc") (50 . 1.5707963268) (51 . -3.1415926536))
((0 . "ARC") (100 . "AcDbEntity") (67 . 0) (8 . "A-Window") (62 . 7) (6 . "Continuous") (100 . "AcDbCircle") (10 51.9421120915 -8.0973569590 0.0000000000) (40 . 0.3000000000) (210 0.0000000000 0.0000000000 1.0000000000) (100 . "AcDbArc") (50 . -3.1415926536) (51 . -1.5707963268))
((0 . "ARC") (100 . "AcDbEntity") (67 . 0) (8 . "A-Window") (62 . 7) (6 . "Continuous") (100 . "AcDbCircle") (10 59.0421120915 -8.0973569590 0.0000000000) (40 . 0.3000000000) (210 0.0000000000 0.0000000000 1.0000000000) (100 . "AcDbArc") (50 . -1.5707963268) (51 . 0.0000000000))
((0 . "ARC") (100 . "AcDbEntity") (67 . 0) (8 . "A-Window") (62 . 7) (6 . "Continuous") (100 . "AcDbCircle") (10 59.0421120915 -4.4973569590 0.0000000000) (40 . 0.3000000000) (210 0.0000000000 0.0000000000 1.0000000000) (100 . "AcDbArc") (50 . 0.0000000000) (51 . 1.5707963268))
((0 . "ARC") (100 . "AcDbEntity") (67 . 0) (8 . "A-Window") (62 . 7) (6 . "Continuous") (100 . "AcDbCircle") (10 58.6421120915 -4.4973569590 0.0000000000) (40 . 0.3000000000) (210 0.0000000000 0.0000000000 1.0000000000) (100 . "AcDbArc") (50 . 1.5707963268) (51 . -3.1415926536))
((0 . "ARC") (100 . "AcDbEntity") (67 . 0) (8 . "A-Window") (62 . 7) (6 . "Continuous") (100 . "AcDbCircle") (10 58.0421120915 -7.0973569590 0.0000000000) (40 . 0.3000000000) (210 0.0000000000 0.0000000000 1.0000000000) (100 . "AcDbArc") (50 . -1.5707963268) (51 . 0.0000000000))
((0 . "ARC") (100 . "AcDbEntity") (67 . 0) (8 . "A-Window") (62 . 7) (6 . "Continuous") (100 . "AcDbCircle") (10 51.9421120915 19.8026430410 0.0000000000) (40 . 0.3000000000) (210 0.0000000000 0.0000000000 1.0000000000) (100 . "AcDbArc") (50 . 1.5707963268) (51 . -3.1415926536))
((0 . "ARC") (100 . "AcDbEntity") (67 . 0) (8 . "A-Window") (62 . 7) (6 . "Continuous") (100 . "AcDbCircle") (10 59.0421120915 19.8026430410 0.0000000000) (40 . 0.3000000000) (210 0.0000000000 0.0000000000 1.0000000000) (100 . "AcDbArc") (50 . 0.0000000000) (51 . 1.5707963268))
((0 . "ARC") (100 . "AcDbEntity") (67 . 0) (8 . "A-Window") (62 . 7) (6 . "Continuous") (100 . "AcDbCircle") (10 59.0421120915 16.2026430410 0.0000000000) (40 . 0.3000000000) (210 0.0000000000 0.0000000000 1.0000000000) (100 . "AcDbArc") (50 . -1.5707963268) (51 . 0.0000000000))
((0 . "ARC") (100 . "AcDbEntity") (67 . 0) (8 . "A-Window") (62 . 7) (6 . "Continuous") (100 . "AcDbCircle") (10 58.6421120915 16.2026430410 0.0000000000) (40 . 0.3000000000) (210 0.0000000000 0.0000000000 1.0000000000) (100 . "AcDbArc") (50 . 3.1415926536) (51 . -1.5707963268))
((0 . "ARC") (100 . "AcDbEntity") (67 . 0) (8 . "A-Window") (62 . 7) (6 . "Continuous") (100 . "AcDbCircle") (10 58.0421120915 18.8026430410 0.0000000000) (40 . 0.3000000000) (210 0.0000000000 0.0000000000 1.0000000000) (100 . "AcDbArc") (50 . 0.0000000000) (51 . 1.5707963268))
((0 . "ARC") (100 . "AcDbEntity") (67 . 0) (8 . "A-Window") (62 . 7) (6 . "Continuous") (100 . "AcDbCircle") (10 53.3421120915 -3.2473569590 0.0000000000) (40 . 0.3000000000) (210 0.0000000000 0.0000000000 1.0000000000) (100 . "AcDbArc") (50 . 0.0000000000) (51 . 1.5707963268))
((0 . "ARC") (100 . "AcDbEntity") (67 . 0) (8 . "A-Window") (62 . 7) (6 . "Continuous") (100 . "AcDbCircle") (10 53.9421120915 -5.8473569590 0.0000000000) (40 . 0.3000000000) (210 0.0000000000 0.0000000000 1.0000000000) (100 . "AcDbArc") (50 . -3.1415926536) (51 . -1.5707963268))
((0 . "ARC") (100 . "AcDbEntity") (67 . 0) (8 . "A-Window") (62 . 7) (6 . "Continuous") (100 . "AcDbCircle") (10 56.5421120915 -5.8473569590 0.0000000000) (40 . 0.3000000000) (210 0.0000000000 0.0000000000 1.0000000000) (100 . "AcDbArc") (50 . -1.5707963268) (51 . 0.0000000000))
((0 . "ARC") (100 . "AcDbEntity") (67 . 0) (8 . "A-Window") (62 . 7) (6 . "Continuous") (100 . "AcDbCircle") (10 56.5421120915 17.5526430410 0.0000000000) (40 . 0.3000000000) (210 0.0000000000 0.0000000000 1.0000000000) (100 . "AcDbArc") (50 . 0.0000000000) (51 . 1.5707963268))
((0 . "ARC") (100 . "AcDbEntity") (67 . 0) (8 . "A-Window") (62 . 7) (6 . "Continuous") (100 . "AcDbCircle") (10 53.9421120915 17.5526430410 0.0000000000) (40 . 0.3000000000) (210 0.0000000000 0.0000000000 1.0000000000) (100 . "AcDbArc") (50 . 1.5707963268) (51 . -3.1415926536))
((0 . "ARC") (100 . "AcDbEntity") (67 . 0) (8 . "A-Window") (62 . 7) (6 . "Continuous") (100 . "AcDbCircle") (10 53.3421120915 14.9526430410 0.0000000000) (40 . 0.3000000000) (210 0.0000000000 0.0000000000 1.0000000000) (100 . "AcDbArc") (50 . -1.5707963268) (51 . 0.0000000000))
((0 . "ARC") (100 . "AcDbEntity") (67 . 0) (8 . "A-Window") (62 . 7) (6 . "Continuous") (100 . "AcDbCircle") (10 58.8421120915 15.3026430410 0.0000000000) (40 . 0.3000000000) (210 0.0000000000 0.0000000000 1.0000000000) (100 . "AcDbArc") (50 . 0.0000000000) (51 . 1.5707963268))
((0 . "ARC") (100 . "AcDbEntity") (67 . 0) (8 . "A-Window") (62 . 7) (6 . "Continuous") (100 . "AcDbCircle") (10 58.2421120915 15.9026430410 0.0000000000) (40 . 0.3000000000) (210 0.0000000000 0.0000000000 1.0000000000) (100 . "AcDbArc") (50 . -3.1415926536) (51 . -1.5707963268))
((0 . "ARC") (100 . "AcDbEntity") (67 . 0) (8 . "A-Window") (62 . 7) (6 . "Continuous") (100 . "AcDbCircle") (10 58.8421120915 -3.5973569590 0.0000000000) (40 . 0.3000000000) (210 0.0000000000 0.0000000000 1.0000000000) (100 . "AcDbArc") (50 . -1.5707963268) (51 . 0.0000000000))
((0 . "ARC") (100 . "AcDbEntity") (67 . 0) (8 . "A-Window") (62 . 7) (6 . "Continuous") (100 . "AcDbCircle") (10 58.2421120915 -4.1973569590 0.0000000000) (40 . 0.3000000000) (210 0.0000000000 0.0000000000 1.0000000000) (100 . "AcDbArc") (50 . 1.5707963268) (51 . -3.1415926536))
((0 . "LINE") (100 . "AcDbEntity") (67 . 0) (8 . "A-Window") (62 . 7) (6 . "Continuous") (100 . "AcDbLine") (10 950.6421111584 5.8602784855 0.0000000000) (11 950.6421111584 5.8457778704 0.0000000000) (210 0.0000000000 0.0000000000 1.0000000000))
((0 . "LINE") (100 . "AcDbEntity") (67 . 0) (8 . "A-Window") (62 . 7) (6 . "Continuous") (100 . "AcDbLine") (10 952.6421111584 5.8602784855 0.0000000000) (11 952.6421111584 5.8457778704 0.0000000000) (210 0.0000000000 0.0000000000 1.0000000000))
((0 . "LINE") (100 . "AcDbEntity") (67 . 0) (8 . "A-Window") (62 . 7) (6 . "Continuous") (100 . "AcDbLine") (10 950.6421111584 -2.1397215145 0.0000000000) (11 947.6421111584 -2.1397215145 0.0000000000) (210 0.0000000000 0.0000000000 1.0000000000))
((0 . "LINE") (100 . "AcDbEntity") (67 . 0) (8 . "A-Window") (62 . 7) (6 . "Continuous") (100 . "AcDbLine") (10 950.6421111584 -2.1397215145 0.0000000000) (11 950.6421111584 5.8457778704 0.0000000000) (210 0.0000000000 0.0000000000 1.0000000000))
((0 . "LINE") (100 . "AcDbEntity") (67 . 0) (8 . "A-Window") (62 . 7) (6 . "Continuous") (100 . "AcDbLine") (10 952.6421111584 -2.1397215145 0.0000000000) (11 950.6421111584 -2.1397215145 0.0000000000) (210 0.0000000000 0.0000000000 1.0000000000))
((0 . "LINE") (100 . "AcDbEntity") (67 . 0) (8 . "A-Window") (62 . 7) (6 . "Continuous") (100 . "AcDbLine") (10 952.6421111584 5.8457778704 0.0000000000) (11 952.6421111584 -2.1397215145 0.0000000000) (210 0.0000000000 0.0000000000 1.0000000000))
((0 . "LINE") (100 . "AcDbEntity") (67 . 0) (8 . "A-Window") (62 . 7) (6 . "Continuous") (100 . "AcDbLine") (10 950.6421111584 13.8573850862 0.0000000000) (11 947.6421111584 13.8573850862 0.0000000000) (210 0.0000000000 0.0000000000 1.0000000000))
((0 . "LINE") (100 . "AcDbEntity") (67 . 0) (8 . "A-Window") (62 . 7) (6 . "Continuous") (100 . "AcDbLine") (10 952.6421111584 13.8573850862 0.0000000000) (11 952.6421111584 5.8602784855 0.0000000000) (210 0.0000000000 0.0000000000 1.0000000000))
((0 . "LINE") (100 . "AcDbEntity") (67 . 0) (8 . "A-Window") (62 . 7) (6 . "Continuous") (100 . "AcDbLine") (10 950.6421111584 13.8573850862 0.0000000000) (11 952.6421111584 13.8573850862 0.0000000000) (210 0.0000000000 0.0000000000 1.0000000000))
((0 . "LINE") (100 . "AcDbEntity") (67 . 0) (8 . "A-Window") (62 . 7) (6 . "Continuous") (100 . "AcDbLine") (10 950.6421111584 5.8602784855 0.0000000000) (11 950.6421111584 13.8573850862 0.0000000000) (210 0.0000000000 0.0000000000 1.0000000000))
((0 . "LINE") (100 . "AcDbEntity") (67 . 0) (8 . "A-Window") (62 . 7) (6 . "Continuous") (100 . "AcDbLine") (10 941.3421111584 18.8573850862 0.0000000000) (11 941.4421111584 18.8573850862 0.0000000000) (210 0.0000000000 0.0000000000 1.0000000000))
((0 . "LINE") (100 . "AcDbEntity") (67 . 0) (8 . "A-Window") (62 . 7) (6 . "Continuous") (100 . "AcDbLine") (10 941.3421111584 15.9073850862 0.0000000000) (11 941.3421111584 18.8573850862 0.0000000000) (210 0.0000000000 0.0000000000 1.0000000000))
((0 . "LINE") (100 . "AcDbEntity") (67 . 0) (8 . "A-Window") (62 . 7) (6 . "Continuous") (100 . "AcDbLine") (10 940.4421111584 15.6073850862 0.0000000000) (11 941.0421111584 15.6073850862 0.0000000000) (210 0.0000000000 0.0000000000 1.0000000000))
((0 . "LINE") (100 . "AcDbEntity") (67 . 0) (8 . "A-Window") (62 . 7) (6 . "Continuous") (100 . "AcDbLine") (10 940.1421111584 -3.5926149138 0.0000000000) (11 940.1421111584 -2.1397215145 0.0000000000) (210 0.0000000000 0.0000000000 1.0000000000))
((0 . "LINE") (100 . "AcDbEntity") (67 . 0) (8 . "A-Window") (62 . 7) (6 . "Continuous") (100 . "AcDbLine") (10 940.1421111584 13.8573850862 0.0000000000) (11 940.1421111584 15.3073850862 0.0000000000) (210 0.0000000000 0.0000000000 1.0000000000))
((0 . "LINE") (100 . "AcDbEntity") (67 . 0) (8 . "A-Window") (62 . 7) (6 . "Continuous") (100 . "AcDbLine") (10 941.0421111584 -3.8926149138 0.0000000000) (11 940.4421111584 -3.8926149138 0.0000000000) (210 0.0000000000 0.0000000000 1.0000000000))
((0 . "LINE") (100 . "AcDbEntity") (67 . 0) (8 . "A-Window") (62 . 7) (6 . "Continuous") (100 . "AcDbLine") (10 941.3421111584 -7.1426149138 0.0000000000) (11 941.3421111584 -4.1926149138 0.0000000000) (210 0.0000000000 0.0000000000 1.0000000000))
((0 . "LINE") (100 . "AcDbEntity") (67 . 0) (8 . "A-Window") (62 . 7) (6 . "Continuous") (100 . "AcDbLine") (10 941.4421111584 -7.1426149138 0.0000000000) (11 941.3421111584 -7.1426149138 0.0000000000) (210 0.0000000000 0.0000000000 1.0000000000))
((0 . "LINE") (100 . "AcDbEntity") (67 . 0) (8 . "A-Window") (62 . 7) (6 . "Continuous") (100 . "AcDbLine") (10 945.6421111584 -3.2426149138 0.0000000000) (11 945.6421111584 -5.8426149138 0.0000000000) (210 0.0000000000 0.0000000000 1.0000000000))
((0 . "LINE") (100 . "AcDbEntity") (67 . 0) (8 . "A-Window") (62 . 7) (6 . "Continuous") (100 . "AcDbLine") (10 942.4421111584 15.3573850862 0.0000000000) (11 941.4421111584 15.3573850862 0.0000000000) (210 0.0000000000 0.0000000000 1.0000000000))
((0 . "LINE") (100 . "AcDbEntity") (67 . 0) (8 . "A-Window") (62 . 7) (6 . "Continuous") (100 . "AcDbLine") (10 942.4421111584 -3.6426149138 0.0000000000) (11 941.4421111584 -3.6426149138 0.0000000000) (210 0.0000000000 0.0000000000 1.0000000000))
((0 . "LINE") (100 . "AcDbEntity") (67 . 0) (8 . "A-Window") (62 . 7) (6 . "Continuous") (100 . "AcDbLine") (10 945.9421111584 14.6573850862 0.0000000000) (11 946.6421111584 14.6573850862 0.0000000000) (210 0.0000000000 0.0000000000 1.0000000000))
((0 . "LINE") (100 . "AcDbEntity") (67 . 0) (8 . "A-Window") (62 . 7) (6 . "Continuous") (100 . "AcDbLine") (10 946.6421111584 14.6573850862 0.0000000000) (11 946.6421111584 18.8573850862 0.0000000000) (210 0.0000000000 0.0000000000 1.0000000000))
((0 . "LINE") (100 . "AcDbEntity") (67 . 0) (8 . "A-Window") (62 . 7) (6 . "Continuous") (100 . "AcDbLine") (10 945.6421111584 17.5573850862 0.0000000000) (11 945.6421111584 14.9573850862 0.0000000000) (210 0.0000000000 0.0000000000 1.0000000000))
((0 . "LINE") (100 . "AcDbEntity") (67 . 0) (8 . "A-Window") (62 . 7) (6 . "Continuous") (100 . "AcDbLine") (10 945.3421111584 -6.1426149138 0.0000000000) (11 942.7421111584 -6.1426149138 0.0000000000) (210 0.0000000000 0.0000000000 1.0000000000))
((0 . "LINE") (100 . "AcDbEntity") (67 . 0) (8 . "A-Window") (62 . 7) (6 . "Continuous") (100 . "AcDbLine") (10 946.6421111584 18.8573850862 0.0000000000) (11 941.4421111584 18.8573850862 0.0000000000) (210 0.0000000000 0.0000000000 1.0000000000))
((0 . "LINE") (100 . "AcDbEntity") (67 . 0) (8 . "A-Window") (62 . 7) (6 . "Continuous") (100 . "AcDbLine") (10 941.4421111584 -7.1426149138 0.0000000000) (11 946.6421111584 -7.1426149138 0.0000000000) (210 0.0000000000 0.0000000000 1.0000000000))
((0 . "LINE") (100 . "AcDbEntity") (67 . 0) (8 . "A-Window") (62 . 7) (6 . "Continuous") (100 . "AcDbLine") (10 946.6421111584 -7.1426149138 0.0000000000) (11 946.6421111584 -2.9426149138 0.0000000000) (210 0.0000000000 0.0000000000 1.0000000000))
((0 . "LINE") (100 . "AcDbEntity") (67 . 0) (8 . "A-Window") (62 . 7) (6 . "Continuous") (100 . "AcDbLine") (10 946.6421111584 -2.9426149138 0.0000000000) (11 945.9421111584 -2.9426149138 0.0000000000) (210 0.0000000000 0.0000000000 1.0000000000))
((0 . "LINE") (100 . "AcDbEntity") (67 . 0) (8 . "A-Window") (62 . 7) (6 . "Continuous") (100 . "AcDbLine") (10 942.4421111584 -3.6426149138 0.0000000000) (11 942.4421111584 15.3573850862 0.0000000000) (210 0.0000000000 0.0000000000 1.0000000000))
((0 . "LINE") (100 . "AcDbEntity") (67 . 0) (8 . "A-Window") (62 . 7) (6 . "Continuous") (100 . "AcDbLine") (10 942.4421111584 -5.8426149138 0.0000000000) (11 942.4421111584 -3.6426149138 0.0000000000) (210 0.0000000000 0.0000000000 1.0000000000))
((0 . "LINE") (100 . "AcDbEntity") (67 . 0) (8 . "A-Window") (62 . 7) (6 . "Continuous") (100 . "AcDbLine") (10 942.4421111584 15.3573850862 0.0000000000) (11 942.4421111584 17.5573850862 0.0000000000) (210 0.0000000000 0.0000000000 1.0000000000))
((0 . "LINE") (100 . "AcDbEntity") (67 . 0) (8 . "A-Window") (62 . 7) (6 . "Continuous") (100 . "AcDbLine") (10 942.7421111584 17.8573850862 0.0000000000) (11 945.3421111584 17.8573850862 0.0000000000) (210 0.0000000000 0.0000000000 1.0000000000))
((0 . "LINE") (100 . "AcDbEntity") (67 . 0) (8 . "A-Window") (62 . 7) (6 . "Continuous") (100 . "AcDbLine") (10 941.4421111584 15.3573850862 0.0000000000) (11 941.4421111584 13.8573850862 0.0000000000) (210 0.0000000000 0.0000000000 1.0000000000))
((0 . "LINE") (100 . "AcDbEntity") (67 . 0) (8 . "A-Window") (62 . 7) (6 . "Continuous") (100 . "AcDbLine") (10 941.4421111584 12.5058122017 0.0000000000) (11 941.4421111584 -0.7910420293 0.0000000000) (210 0.0000000000 0.0000000000 1.0000000000))
((0 . "LINE") (100 . "AcDbEntity") (67 . 0) (8 . "A-Window") (62 . 7) (6 . "Continuous") (100 . "AcDbLine") (10 941.4421111584 -2.1397215145 0.0000000000) (11 941.4421111584 -3.6426149138 0.0000000000) (210 0.0000000000 0.0000000000 1.0000000000))
((0 . "LINE") (100 . "AcDbEntity") (67 . 0) (8 . "A-Window") (62 . 7) (6 . "Continuous") (100 . "AcDbLine") (10 941.4421111584 18.8573850862 0.0000000000) (11 941.4421111584 15.3573850862 0.0000000000) (210 0.0000000000 0.0000000000 1.0000000000))
((0 . "LINE") (100 . "AcDbEntity") (67 . 0) (8 . "A-Window") (62 . 7) (6 . "Continuous") (100 . "AcDbLine") (10 941.4421111584 -3.6426149138 0.0000000000) (11 941.4421111584 -7.1426149138 0.0000000000) (210 0.0000000000 0.0000000000 1.0000000000))
((0 . "LINE") (100 . "AcDbEntity") (67 . 0) (8 . "A-Window") (62 . 7) (6 . "Continuous") (100 . "AcDbLine") (10 947.6421111584 19.8073850862 0.0000000000) (11 947.6421111584 -8.0926149138 0.0000000000) (210 0.0000000000 0.0000000000 1.0000000000))
((0 . "LINE") (100 . "AcDbEntity") (67 . 0) (8 . "A-Window") (62 . 7) (6 . "Continuous") (100 . "AcDbLine") (10 946.6421111584 19.1073850862 0.0000000000) (11 941.2421111584 19.1073850862 0.0000000000) (210 0.0000000000 0.0000000000 1.0000000000))
((0 . "LINE") (100 . "AcDbEntity") (67 . 0) (8 . "A-Window") (62 . 7) (6 . "Continuous") (100 . "AcDbLine") (10 946.6421111584 -7.3926149138 0.0000000000) (11 946.6421111584 -7.1426149138 0.0000000000) (210 0.0000000000 0.0000000000 1.0000000000))
((0 . "LINE") (100 . "AcDbEntity") (67 . 0) (8 . "A-Window") (62 . 7) (6 . "Continuous") (100 . "AcDbLine") (10 946.6421111584 -2.9426149138 0.0000000000) (11 946.6421111584 14.6573850862 0.0000000000) (210 0.0000000000 0.0000000000 1.0000000000))
((0 . "LINE") (100 . "AcDbEntity") (67 . 0) (8 . "A-Window") (62 . 7) (6 . "Continuous") (100 . "AcDbLine") (10 946.6421111584 18.8573850862 0.0000000000) (11 946.6421111584 19.1073850862 0.0000000000) (210 0.0000000000 0.0000000000 1.0000000000))
((0 . "LINE") (100 . "AcDbEntity") (67 . 0) (8 . "A-Window") (62 . 7) (6 . "Continuous") (100 . "AcDbLine") (10 947.3421111584 -8.3926149138 0.0000000000) (11 940.2421111584 -8.3926149138 0.0000000000) (210 0.0000000000 0.0000000000 1.0000000000))
((0 . "LINE") (100 . "AcDbEntity") (67 . 0) (8 . "A-Window") (62 . 7) (6 . "Continuous") (100 . "AcDbLine") (10 940.2421111584 20.1073850862 0.0000000000) (11 947.3421111584 20.1073850862 0.0000000000) (210 0.0000000000 0.0000000000 1.0000000000))
((0 . "LINE") (100 . "AcDbEntity") (67 . 0) (8 . "A-Window") (62 . 7) (6 . "Continuous") (100 . "AcDbLine") (10 939.9421111584 16.2073850862 0.0000000000) (11 939.9421111584 19.8073850862 0.0000000000) (210 0.0000000000 0.0000000000 1.0000000000))
((0 . "LINE") (100 . "AcDbEntity") (67 . 0) (8 . "A-Window") (62 . 7) (6 . "Continuous") (100 . "AcDbLine") (10 941.2421111584 -7.3926149138 0.0000000000) (11 946.6421111584 -7.3926149138 0.0000000000) (210 0.0000000000 0.0000000000 1.0000000000))
((0 . "LINE") (100 . "AcDbEntity") (67 . 0) (8 . "A-Window") (62 . 7) (6 . "Continuous") (100 . "AcDbLine") (10 940.9421111584 -4.4926149138 0.0000000000) (11 940.9421111584 -7.0926149138 0.0000000000) (210 0.0000000000 0.0000000000 1.0000000000))
((0 . "LINE") (100 . "AcDbEntity") (67 . 0) (8 . "A-Window") (62 . 7) (6 . "Continuous") (100 . "AcDbLine") (10 939.9421111584 -8.0926149138 0.0000000000) (11 939.9421111584 -4.4926149138 0.0000000000) (210 0.0000000000 0.0000000000 1.0000000000))
((0 . "LINE") (100 . "AcDbEntity") (67 . 0) (8 . "A-Window") (62 . 7) (6 . "Continuous") (100 . "AcDbLine") (10 940.2421111584 -4.1926149138 0.0000000000) (11 940.6421111584 -4.1926149138 0.0000000000) (210 0.0000000000 0.0000000000 1.0000000000))
((0 . "LINE") (100 . "AcDbEntity") (67 . 0) (8 . "A-Window") (62 . 7) (6 . "Continuous") (100 . "AcDbLine") (10 940.9421111584 18.8073850862 0.0000000000) (11 940.9421111584 16.2073850862 0.0000000000) (210 0.0000000000 0.0000000000 1.0000000000))
((0 . "LINE") (100 . "AcDbEntity") (67 . 0) (8 . "A-Window") (62 . 7) (6 . "Continuous") (100 . "AcDbLine") (10 940.6421111584 15.9073850862 0.0000000000) (11 940.2421111584 15.9073850862 0.0000000000) (210 0.0000000000 0.0000000000 1.0000000000))
((0 . "LINE") (100 . "AcDbEntity") (67 . 0) (8 . "A-Window") (62 . 7) (6 . "Continuous") (100 . "AcDbLine") (10 940.8421111584 -2.1426149138 0.0000000000) (11 940.8421111584 -2.1397215145 0.0000000000) (210 0.0000000000 0.0000000000 1.0000000000))
((0 . "LINE") (100 . "AcDbEntity") (67 . 0) (8 . "A-Window") (62 . 7) (6 . "Continuous") (100 . "AcDbLine") (10 941.4421111584 -2.1426149138 0.0000000000) (11 940.8421111584 -2.1426149138 0.0000000000) (210 0.0000000000 0.0000000000 1.0000000000))
((0 . "LINE") (100 . "AcDbEntity") (67 . 0) (8 . "A-Window") (62 . 7) (6 . "Continuous") (100 . "AcDbLine") (10 941.4421111584 13.8573850862 0.0000000000) (11 941.4421111584 12.5058122017 0.0000000000) (210 0.0000000000 0.0000000000 1.0000000000))
((0 . "LINE") (100 . "AcDbEntity") (67 . 0) (8 . "A-Window") (62 . 7) (6 . "Continuous") (100 . "AcDbLine") (10 941.4421111584 -0.7910420293 0.0000000000) (11 941.4421111584 -2.1397215145 0.0000000000) (210 0.0000000000 0.0000000000 1.0000000000))
((0 . "LINE") (100 . "AcDbEntity") (67 . 0) (8 . "A-Window") (62 . 7) (6 . "Continuous") (100 . "AcDbLine") (10 935.6421111598 5.8602784854 0.0000000000) (11 935.6421111598 5.8457778705 0.0000000000) (210 0.0000000000 0.0000000000 1.0000000000))
((0 . "LINE") (100 . "AcDbEntity") (67 . 0) (8 . "A-Window") (62 . 7) (6 . "Continuous") (100 . "AcDbLine") (10 937.6421111598 5.8602784854 0.0000000000) (11 937.6421111598 5.8457778705 0.0000000000) (210 0.0000000000 0.0000000000 1.0000000000))
((0 . "LINE") (100 . "AcDbEntity") (67 . 0) (8 . "A-Window") (62 . 7) (6 . "Continuous") (100 . "AcDbLine") (10 941.4421111584 -2.1397215145 0.0000000000) (11 937.6421111598 -2.1397215145 0.0000000000) (210 0.0000000000 0.0000000000 1.0000000000))
((0 . "LINE") (100 . "AcDbEntity") (67 . 0) (8 . "A-Window") (62 . 7) (6 . "Continuous") (100 . "AcDbLine") (10 935.6421111598 5.8602784854 0.0000000000) (11 935.6421111598 13.8573850862 0.0000000000) (210 0.0000000000 0.0000000000 1.0000000000))
((0 . "LINE") (100 . "AcDbEntity") (67 . 0) (8 . "A-Window") (62 . 7) (6 . "Continuous") (100 . "AcDbLine") (10 937.6421111598 13.8573850862 0.0000000000) (11 937.6421111598 5.8602784854 0.0000000000) (210 0.0000000000 0.0000000000 1.0000000000))
((0 . "LINE") (100 . "AcDbEntity") (67 . 0) (8 . "A-Window") (62 . 7) (6 . "Continuous") (100 . "AcDbLine") (10 937.6421111598 5.8457778705 0.0000000000) (11 937.6421111598 -2.1397215145 0.0000000000) (210 0.0000000000 0.0000000000 1.0000000000))
((0 . "LINE") (100 . "AcDbEntity") (67 . 0) (8 . "A-Window") (62 . 7) (6 . "Continuous") (100 . "AcDbLine") (10 935.6421111598 -2.1397215145 0.0000000000) (11 935.6421111598 5.8457778705 0.0000000000) (210 0.0000000000 0.0000000000 1.0000000000))
((0 . "LINE") (100 . "AcDbEntity") (67 . 0) (8 . "A-Window") (62 . 7) (6 . "Continuous") (100 . "AcDbLine") (10 937.6421111598 -2.1397215145 0.0000000000) (11 935.6421111598 -2.1397215145 0.0000000000) (210 0.0000000000 0.0000000000 1.0000000000))
((0 . "LINE") (100 . "AcDbEntity") (67 . 0) (8 . "A-Window") (62 . 7) (6 . "Continuous") (100 . "AcDbLine") (10 937.6421111598 13.8573850862 0.0000000000) (11 935.6421111598 13.8573850862 0.0000000000) (210 0.0000000000 0.0000000000 1.0000000000))
((0 . "LINE") (100 . "AcDbEntity") (67 . 0) (8 . "A-Window") (62 . 7) (6 . "Continuous") (100 . "AcDbLine") (10 941.4421111584 13.8573850862 0.0000000000) (11 937.6421111598 13.8573850862 0.0000000000) (210 0.0000000000 0.0000000000 1.0000000000))
((0 . "LINE") (100 . "AcDbEntity") (67 . 0) (8 . "A-Window") (62 . 7) (6 . "Continuous") (100 . "AcDbLine") (10 942.4421111584 10.2073850862 0.0000000000) (11 942.6421111584 10.2073850862 0.0000000000) (210 0.0000000000 0.0000000000 1.0000000000))
((0 . "LINE") (100 . "AcDbEntity") (67 . 0) (8 . "A-Window") (62 . 7) (6 . "Continuous") (100 . "AcDbLine") (10 942.4421111584 1.5073850862 0.0000000000) (11 942.6421111584 1.5073850862 0.0000000000) (210 0.0000000000 0.0000000000 1.0000000000))
((0 . "LINE") (100 . "AcDbEntity") (67 . 0) (8 . "A-Window") (62 . 7) (6 . "Continuous") (100 . "AcDbLine") (10 943.6921111584 2.5573850862 0.0000000000) (11 943.6921111584 9.1573850862 0.0000000000) (210 0.0000000000 0.0000000000 1.0000000000))
((0 . "ARC") (100 . "AcDbEntity") (67 . 0) (8 . "A-Window") (62 . 7) (6 . "Continuous") (100 . "AcDbCircle") (10 -942.6421111584 2.5573850862 0.0000000000) (40 . 1.0500000000) (210 0.0000000000 0.0000000000 -1.0000000000) (100 . "AcDbArc") (50 . 3.1415926536) (51 . -1.5707963268))
((0 . "ARC") (100 . "AcDbEntity") (67 . 0) (8 . "A-Window") (62 . 7) (6 . "Continuous") (100 . "AcDbCircle") (10 -942.6421111584 9.1573850862 0.0000000000) (40 . 1.0500000000) (210 0.0000000000 0.0000000000 -1.0000000000) (100 . "AcDbArc") (50 . 1.5707963268) (51 . 3.1415926536))
((0 . "ARC") (100 . "AcDbEntity") (67 . 0) (8 . "A-Window") (62 . 7) (6 . "Continuous") (100 . "AcDbCircle") (10 -947.3421111584 -8.0926149138 0.0000000000) (40 . 0.3000000000) (210 0.0000000000 0.0000000000 -1.0000000000) (100 . "AcDbArc") (50 . 3.1415926536) (51 . -1.5707963268))
((0 . "ARC") (100 . "AcDbEntity") (67 . 0) (8 . "A-Window") (62 . 7) (6 . "Continuous") (100 . "AcDbCircle") (10 -940.2421111584 -8.0926149138 0.0000000000) (40 . 0.3000000000) (210 0.0000000000 0.0000000000 -1.0000000000) (100 . "AcDbArc") (50 . -1.5707963268) (51 . 0.0000000000))
((0 . "ARC") (100 . "AcDbEntity") (67 . 0) (8 . "A-Window") (62 . 7) (6 . "Continuous") (100 . "AcDbCircle") (10 -940.2421111584 -4.4926149138 0.0000000000) (40 . 0.3000000000) (210 0.0000000000 0.0000000000 -1.0000000000) (100 . "AcDbArc") (50 . 0.0000000000) (51 . 1.5707963268))
((0 . "ARC") (100 . "AcDbEntity") (67 . 0) (8 . "A-Window") (62 . 7) (6 . "Continuous") (100 . "AcDbCircle") (10 -940.6421111584 -4.4926149138 0.0000000000) (40 . 0.3000000000) (210 0.0000000000 0.0000000000 -1.0000000000) (100 . "AcDbArc") (50 . 1.5707963268) (51 . 3.1415926536))
((0 . "ARC") (100 . "AcDbEntity") (67 . 0) (8 . "A-Window") (62 . 7) (6 . "Continuous") (100 . "AcDbCircle") (10 -941.2421111584 -7.0926149138 0.0000000000) (40 . 0.3000000000) (210 0.0000000000 0.0000000000 -1.0000000000) (100 . "AcDbArc") (50 . -1.5707963268) (51 . 0.0000000000))
((0 . "ARC") (100 . "AcDbEntity") (67 . 0) (8 . "A-Window") (62 . 7) (6 . "Continuous") (100 . "AcDbCircle") (10 -947.3421111584 19.8073850862 0.0000000000) (40 . 0.3000000000) (210 0.0000000000 0.0000000000 -1.0000000000) (100 . "AcDbArc") (50 . 1.5707963268) (51 . 3.1415926536))
((0 . "ARC") (100 . "AcDbEntity") (67 . 0) (8 . "A-Window") (62 . 7) (6 . "Continuous") (100 . "AcDbCircle") (10 -940.2421111584 19.8073850862 0.0000000000) (40 . 0.3000000000) (210 0.0000000000 0.0000000000 -1.0000000000) (100 . "AcDbArc") (50 . 0.0000000000) (51 . 1.5707963268))
((0 . "ARC") (100 . "AcDbEntity") (67 . 0) (8 . "A-Window") (62 . 7) (6 . "Continuous") (100 . "AcDbCircle") (10 -940.2421111584 16.2073850862 0.0000000000) (40 . 0.3000000000) (210 0.0000000000 0.0000000000 -1.0000000000) (100 . "AcDbArc") (50 . -1.5707963268) (51 . 0.0000000000))
((0 . "ARC") (100 . "AcDbEntity") (67 . 0) (8 . "A-Window") (62 . 7) (6 . "Continuous") (100 . "AcDbCircle") (10 -940.6421111584 16.2073850862 0.0000000000) (40 . 0.3000000000) (210 0.0000000000 0.0000000000 -1.0000000000) (100 . "AcDbArc") (50 . 3.1415926536) (51 . -1.5707963268))
((0 . "ARC") (100 . "AcDbEntity") (67 . 0) (8 . "A-Window") (62 . 7) (6 . "Continuous") (100 . "AcDbCircle") (10 -941.2421111584 18.8073850862 0.0000000000) (40 . 0.3000000000) (210 0.0000000000 0.0000000000 -1.0000000000) (100 . "AcDbArc") (50 . 0.0000000000) (51 . 1.5707963268))
((0 . "ARC") (100 . "AcDbEntity") (67 . 0) (8 . "A-Window") (62 . 7) (6 . "Continuous") (100 . "AcDbCircle") (10 -945.9421111584 -3.2426149138 0.0000000000) (40 . 0.3000000000) (210 0.0000000000 0.0000000000 -1.0000000000) (100 . "AcDbArc") (50 . 0.0000000000) (51 . 1.5707963268))
((0 . "ARC") (100 . "AcDbEntity") (67 . 0) (8 . "A-Window") (62 . 7) (6 . "Continuous") (100 . "AcDbCircle") (10 -945.3421111584 -5.8426149138 0.0000000000) (40 . 0.3000000000) (210 0.0000000000 0.0000000000 -1.0000000000) (100 . "AcDbArc") (50 . 3.1415926536) (51 . -1.5707963268))
((0 . "ARC") (100 . "AcDbEntity") (67 . 0) (8 . "A-Window") (62 . 7) (6 . "Continuous") (100 . "AcDbCircle") (10 -942.7421111584 -5.8426149138 0.0000000000) (40 . 0.3000000000) (210 0.0000000000 0.0000000000 -1.0000000000) (100 . "AcDbArc") (50 . -1.5707963268) (51 . 0.0000000000))
((0 . "ARC") (100 . "AcDbEntity") (67 . 0) (8 . "A-Window") (62 . 7) (6 . "Continuous") (100 . "AcDbCircle") (10 -942.7421111584 17.5573850862 0.0000000000) (40 . 0.3000000000) (210 0.0000000000 0.0000000000 -1.0000000000) (100 . "AcDbArc") (50 . 0.0000000000) (51 . 1.5707963268))
((0 . "ARC") (100 . "AcDbEntity") (67 . 0) (8 . "A-Window") (62 . 7) (6 . "Continuous") (100 . "AcDbCircle") (10 -945.3421111584 17.5573850862 0.0000000000) (40 . 0.3000000000) (210 0.0000000000 0.0000000000 -1.0000000000) (100 . "AcDbArc") (50 . 1.5707963268) (51 . -3.1415926536))
((0 . "ARC") (100 . "AcDbEntity") (67 . 0) (8 . "A-Window") (62 . 7) (6 . "Continuous") (100 . "AcDbCircle") (10 -945.9421111584 14.9573850862 0.0000000000) (40 . 0.3000000000) (210 0.0000000000 0.0000000000 -1.0000000000) (100 . "AcDbArc") (50 . -1.5707963268) (51 . 0.0000000000))
((0 . "ARC") (100 . "AcDbEntity") (67 . 0) (8 . "A-Window") (62 . 7) (6 . "Continuous") (100 . "AcDbCircle") (10 -940.4421111584 15.3073850862 0.0000000000) (40 . 0.3000000000) (210 0.0000000000 0.0000000000 -1.0000000000) (100 . "AcDbArc") (50 . 0.0000000000) (51 . 1.5707963268))
((0 . "ARC") (100 . "AcDbEntity") (67 . 0) (8 . "A-Window") (62 . 7) (6 . "Continuous") (100 . "AcDbCircle") (10 -941.0421111584 15.9073850862 0.0000000000) (40 . 0.3000000000) (210 0.0000000000 0.0000000000 -1.0000000000) (100 . "AcDbArc") (50 . 3.1415926536) (51 . -1.5707963268))
((0 . "ARC") (100 . "AcDbEntity") (67 . 0) (8 . "A-Window") (62 . 7) (6 . "Continuous") (100 . "AcDbCircle") (10 -940.4421111584 -3.5926149138 0.0000000000) (40 . 0.3000000000) (210 0.0000000000 0.0000000000 -1.0000000000) (100 . "AcDbArc") (50 . -1.5707963268) (51 . 0.0000000000))
((0 . "ARC") (100 . "AcDbEntity") (67 . 0) (8 . "A-Window") (62 . 7) (6 . "Continuous") (100 . "AcDbCircle") (10 -941.0421111584 -4.1926149138 0.0000000000) (40 . 0.3000000000) (210 0.0000000000 0.0000000000 -1.0000000000) (100 . "AcDbArc") (50 . 1.5707963268) (51 . 3.1415926536))
((0 . "LWPOLYLINE") (100 . "AcDbEntity") (67 . 0) (8 . "A-Window") (62 . 151) (6 . "Continuous") (100 . "AcDbPolyline") (90 . 63) (70 . 1) (43 . 0.0000000000) (38 . 0.0000000000) (39 . 0.0000000000) (10 -32.1421111606 19.8553443463) (40 . 0.0000000000) (41 . 0.0000000000) (42 . 0.0000000000) (91 . 0) (10 -32.1421111606 19.6553443463) (40 . 0.0000000000) (41 . 0.0000000000) (42 . -0.4142135624) (91 . 0) (10 -32.6421111606 19.1553443463) (40 . 0.0000000000) (41 . 0.0000000000) (42 . 0.0000000000) (91 . 0) (10 -35.8421111606 19.1553443463) (40 . 0.0000000000) (41 . 0.0000000000) (42 . 0.4142135624) (91 . 0) (10 -36.3421111606 18.6553443463) (40 . 0.0000000000) (41 . 0.0000000000) (42 . 0.0000000000) (91 . 0) (10 -36.3421111606 11.8553443463) (40 . 0.0000000000) (41 . 0.0000000000) (42 . 0.4142135624) (91 . 0) (10 -35.8421111606 11.3553443463) (40 . 0.0000000000) (41 . 0.0000000000) (42 . 0.0000000000) (91 . 0) (10 -32.6421111606 11.3553443463) (40 . 0.0000000000) (41 . 0.0000000000) (42 . -0.4142135624) (91 . 0) (10 -32.1421111606 10.8553443463) (40 . 0.0000000000) (41 . 0.0000000000) (42 . 0.0000000000) (91 . 0) (10 -32.1421111606 9.8553443463) (40 . 0.0000000000) (41 . 0.0000000000) (42 . -0.4142135624) (91 . 0) (10 -32.6421111606 9.3553443463) (40 . 0.0000000000) (41 . 0.0000000000) (42 . 0.0000000000) (91 . 0) (10 -35.8421111606 9.3553443463) (40 . 0.0000000000) (41 . 0.0000000000) (42 . 0.4142135624) (91 . 0) (10 -36.3421111606 8.8553443463) (40 . 0.0000000000) (41 . 0.0000000000) (42 . 0.0000000000) (91 . 0) (10 -36.3421111606 -24.1446556537) (40 . 0.0000000000) (41 . 0.0000000000) (42 . 0.4142135624) (91 . 0) (10 -35.8421111606 -24.6446556537) (40 . 0.0000000000) (41 . 0.0000000000) (42 . 0.0000000000) (91 . 0) (10 -32.6421111606 -24.6446556537) (40 . 0.0000000000) (41 . 0.0000000000) (42 . -0.4142135624) (91 . 0) (10 -32.1421111606 -25.1446556537) (40 . 0.0000000000) (41 . 0.0000000000) (42 . 0.0000000000) (91 . 0) (10 -32.1421111606 -26.1446556537) (40 . 0.0000000000) (41 . 0.0000000000) (42 . -0.4142135624) (91 . 0) (10 -32.6421111606 -26.6446556537) (40 . 0.0000000000) (41 . 0.0000000000) (42 . 0.0000000000) (91 . 0) (10 -35.8421111606 -26.6446556537) (40 . 0.0000000000) (41 . 0.0000000000) (42 . 0.4142135624) (91 . 0) (10 -36.3421111606 -27.1446556537) (40 . 0.0000000000) (41 . 0.0000000000) (42 . 0.0000000000) (91 . 0) (10 -36.3421111606 -29.1446556537) (40 . 0.0000000000) (41 . 0.0000000000) (42 . -0.4142135624) (91 . 0) (10 -36.8421111606 -29.6446556537) (40 . 0.0000000000) (41 . 0.0000000000) (42 . 0.0000000000) (91 . 0) (10 -77.8421111606 -29.6446556537) (40 . 0.0000000000) (41 . 0.0000000000) (42 . -0.4142135624) (91 . 0) (10 -78.3421111606 -29.1446556537) (40 . 0.0000000000) (41 . 0.0000000000) (42 . 0.0000000000) (91 . 0) (10 -78.3421111606 -26.1446556537) (40 . 0.0000000000) (41 . 0.0000000000) (42 . -0.4142135624) (91 . 0) (10 -77.8421111606 -25.6446556537) (40 . 0.0000000000) (41 . 0.0000000000) (42 . 0.0000000000) (91 . 0) (10 -76.1421111605 -25.6446556537) (40 . 0.0000000000) (41 . 0.0000000000) (42 . -0.4142135624) (91 . 0) (10 -75.6421111605 -26.1446556537) (40 . 0.0000000000) (41 . 0.0000000000) (42 . -0.4142135624) (91 . 0) (10 -76.1421111604 -26.6446556537) (40 . 0.0000000000) (41 . 0.0000000000) (42 . 0.0000000000) (91 . 0) (10 -76.3421111606 -26.6446556537) (40 . 0.0000000000) (41 . 0.0000000000) (42 . 0.4142135624) (91 . 0) (10 -76.8421111606 -27.1446556537) (40 . 0.0000000000) (41 . 0.0000000000) (42 . 0.0000000000) (91 . 0) (10 -76.8421111606 -27.5446556537) (40 . 0.0000000000) (41 . 0.0000000000) (42 . 0.4142135624) (91 . 0) (10 -76.3421111606 -28.0446556537) (40 . 0.0000000000) (41 . 0.0000000000) (42 . 0.0000000000) (91 . 0) (10 -71.3421111606 -28.0446556537) (40 . 0.0000000000) (41 . 0.0000000000) (42 . 0.4142135624) (91 . 0) (10 -70.8421111606 -27.5446556537) (40 . 0.0000000000) (41 . 0.0000000000) (42 . 0.0000000000) (91 . 0) (10 -70.8421111606 -27.1446556537) (40 . 0.0000000000) (41 . 0.0000000000) (42 . 0.4142135624) (91 . 0) (10 -71.3421111606 -26.6446556537) (40 . 0.0000000000) (41 . 0.0000000000) (42 . 0.0000000000) (91 . 0) (10 -71.5421111607 -26.6446556537) (40 . 0.0000000000) (41 . 0.0000000000) (42 . -0.4142135624) (91 . 0) (10 -72.0421111607 -26.1446556537) (40 . 0.0000000000) (41 . 0.0000000000) (42 . 0.0000000000) (91 . 0) (10 -72.0421111607 -26.1446556537) (40 . 0.0000000000) (41 . 0.0000000000) (42 . -0.4142135624) (91 . 0) (10 -71.5421111607 -25.6446556537) (40 . 0.0000000000) (41 . 0.0000000000) (42 . 0.0000000000) (91 . 0) (10 -69.8421111606 -25.6446556537) (40 . 0.0000000000) (41 . 0.0000000000) (42 . -0.4142135624) (91 . 0) (10 -69.3421111606 -26.1446556537) (40 . 0.0000000000) (41 . 0.0000000000) (42 . 0.0000000000) (91 . 0) (10 -69.3421111606 -27.6446556537) (40 . 0.0000000000) (41 . 0.0000000000) (42 . 0.4142135624) (91 . 0) (10 -68.8421111606 -28.1446556537) (40 . 0.0000000000) (41 . 0.0000000000) (42 . 0.0000000000) (91 . 0) (10 -47.1421111606 -28.1446556537) (40 . 0.0000000000) (41 . 0.0000000000) (42 . 0.4142135624) (91 . 0) (10 -46.6421111606 -27.6446556537) (40 . 0.0000000000) (41 . 0.0000000000) (42 . 0.0000000000) (91 . 0) (10 -46.6421111606 -4.6431837911) (40 . 0.0000000000) (41 . 0.0000000000) (42 . -0.1989123674) (91 . 0) (10 -46.5542431949 -4.4310517567) (40 . 0.0000000000) (41 . 0.0000000000) (42 . 0.0000000000) (91 . 0) (10 -46.2299791262 -4.1067876880) (40 . 0.0000000000) (41 . 0.0000000000) (42 . 0.4142135624) (91 . 0) (10 -46.2299791262 -3.6825236193) (40 . 0.0000000000) (41 . 0.0000000000) (42 . 0.0000000000) (91 . 0) (10 -46.5542431949 -3.3582595506) (40 . 0.0000000000) (41 . 0.0000000000) (42 . -0.1989123674) (91 . 0) (10 -46.6421111606 -3.1461275163) (40 . 0.0000000000) (41 . 0.0000000000) (42 . 0.0000000000) (91 . 0) (10 -46.6421111606 5.1068162089) (40 . 0.0000000000) (41 . 0.0000000000) (42 . -0.1989123674) (91 . 0) (10 -46.5542431949 5.3189482433) (40 . 0.0000000000) (41 . 0.0000000000) (42 . 0.0000000000) (91 . 0) (10 -46.2299791262 5.6432123120) (40 . 0.0000000000) (41 . 0.0000000000) (42 . 0.4142135624) (91 . 0) (10 -46.2299791262 6.0674763807) (40 . 0.0000000000) (41 . 0.0000000000) (42 . 0.0000000000) (91 . 0) (10 -46.5542431949 6.3917404494) (40 . 0.0000000000) (41 . 0.0000000000) (42 . -0.1989123674) (91 . 0) (10 -46.6421111606 6.6038724837) (40 . 0.0000000000) (41 . 0.0000000000) (42 . 0.0000000000) (91 . 0) (10 -46.6421111606 19.8553443463) (40 . 0.0000000000) (41 . 0.0000000000) (42 . -0.4142135624) (91 . 0) (10 -46.1421111606 20.3553443463) (40 . 0.0000000000) (41 . 0.0000000000) (42 . 0.0000000000) (91 . 0) (10 -32.6421111606 20.3553443463) (40 . 0.0000000000) (41 . 0.0000000000) (42 . -0.4142135624) (91 . 0) (210 0.0000000000 0.0000000000 -1.0000000000))
((0 . "LWPOLYLINE") (100 . "AcDbEntity") (67 . 0) (8 . "A-Window") (62 . 151) (6 . "Continuous") (100 . "AcDbPolyline") (90 . 24) (70 . 1) (43 . 0.0000000000) (38 . 0.0000000000) (39 . 0.0000000000) (10 -38.1421111606 -28.1446556537) (40 . 0.0000000000) (41 . 0.0000000000) (42 . 0.4142135624) (91 . 0) (10 -37.8421111606 -27.8446556537) (40 . 0.0000000000) (41 . 0.0000000000) (42 . 0.0000000000) (91 . 0) (10 -37.8421111606 15.5553443463) (40 . 0.0000000000) (41 . 0.0000000000) (42 . 0.4142135624) (91 . 0) (10 -38.1421111606 15.8553443463) (40 . 0.0000000000) (41 . 0.0000000000) (42 . 0.0000000000) (91 . 0) (10 -38.8421111606 15.8553443463) (40 . 0.0000000000) (41 . 0.0000000000) (42 . -0.4142135624) (91 . 0) (10 -39.3421111606 16.3553443463) (40 . 0.0000000000) (41 . 0.0000000000) (42 . 0.0000000000) (91 . 0) (10 -39.3421111606 16.5553443463) (40 . 0.0000000000) (41 . 0.0000000000) (42 . -0.4142135624) (91 . 0) (10 -38.8421111606 17.0553443463) (40 . 0.0000000000) (41 . 0.0000000000) (42 . 0.0000000000) (91 . 0) (10 -38.3421111606 17.0553443463) (40 . 0.0000000000) (41 . 0.0000000000) (42 . 0.4142135624) (91 . 0) (10 -37.8421111606 17.5553443463) (40 . 0.0000000000) (41 . 0.0000000000) (42 . 0.0000000000) (91 . 0) (10 -37.8421111606 18.3553443463) (40 . 0.0000000000) (41 . 0.0000000000) (42 . 0.4142135624) (91 . 0) (10 -38.3421111606 18.8553443463) (40 . 0.0000000000) (41 . 0.0000000000) (42 . 0.0000000000) (91 . 0) (10 -44.1421111606 18.8553443463) (40 . 0.0000000000) (41 . 0.0000000000) (42 . 0.4142135624) (91 . 0) (10 -44.6421111606 18.3553443463) (40 . 0.0000000000) (41 . 0.0000000000) (42 . 0.0000000000) (91 . 0) (10 -44.6421111606 17.5553443463) (40 . 0.0000000000) (41 . 0.0000000000) (42 . 0.4142135624) (91 . 0) (10 -44.1421111606 17.0553443463) (40 . 0.0000000000) (41 . 0.0000000000) (42 . 0.0000000000) (91 . 0) (10 -43.6421111606 17.0553443463) (40 . 0.0000000000) (41 . 0.0000000000) (42 . -0.4142135624) (91 . 0) (10 -43.1421111606 16.5553443463) (40 . 0.0000000000) (41 . 0.0000000000) (42 . 0.0000000000) (91 . 0) (10 -43.1421111606 16.3553443463) (40 . 0.0000000000) (41 . 0.0000000000) (42 . -0.4142135624) (91 . 0) (10 -43.6421111606 15.8553443463) (40 . 0.0000000000) (41 . 0.0000000000) (42 . 0.0000000000) (91 . 0) (10 -44.3421111606 15.8553443463) (40 . 0.0000000000) (41 . 0.0000000000) (42 . 0.4142135624) (91 . 0) (10 -44.6421111606 15.5553443463) (40 . 0.0000000000) (41 . 0.0000000000) (42 . 0.0000000000) (91 . 0) (10 -44.6421111606 -27.8446556537) (40 . 0.0000000000) (41 . 0.0000000000) (42 . 0.4142135624) (91 . 0) (10 -44.3421111606 -28.1446556537) (40 . 0.0000000000) (41 . 0.0000000000) (42 . 0.0000000000) (91 . 0) (210 0.0000000000 0.0000000000 -1.0000000000))
((0 . "LWPOLYLINE") (100 . "AcDbEntity") (67 . 0) (8 . "A-Window") (62 . 151) (6 . "Continuous") (100 . "AcDbPolyline") (90 . 63) (70 . 1) (43 . 0.0000000000) (38 . 0.0000000000) (39 . 0.0000000000) (10 -967.1421111598 19.8553443461) (40 . 0.0000000000) (41 . 0.0000000000) (42 . 0.0000000000) (91 . 0) (10 -967.1421111598 19.6553443461) (40 . 0.0000000000) (41 . 0.0000000000) (42 . 0.4142135624) (91 . 0) (10 -966.6421111598 19.1553443461) (40 . 0.0000000000) (41 . 0.0000000000) (42 . 0.0000000000) (91 . 0) (10 -963.4421111598 19.1553443461) (40 . 0.0000000000) (41 . 0.0000000000) (42 . -0.4142135624) (91 . 0) (10 -962.9421111598 18.6553443461) (40 . 0.0000000000) (41 . 0.0000000000) (42 . 0.0000000000) (91 . 0) (10 -962.9421111598 11.8553443461) (40 . 0.0000000000) (41 . 0.0000000000) (42 . -0.4142135624) (91 . 0) (10 -963.4421111598 11.3553443461) (40 . 0.0000000000) (41 . 0.0000000000) (42 . 0.0000000000) (91 . 0) (10 -966.6421111598 11.3553443461) (40 . 0.0000000000) (41 . 0.0000000000) (42 . 0.4142135624) (91 . 0) (10 -967.1421111598 10.8553443461) (40 . 0.0000000000) (41 . 0.0000000000) (42 . 0.0000000000) (91 . 0) (10 -967.1421111598 9.8553443461) (40 . 0.0000000000) (41 . 0.0000000000) (42 . 0.4142135624) (91 . 0) (10 -966.6421111598 9.3553443461) (40 . 0.0000000000) (41 . 0.0000000000) (42 . 0.0000000000) (91 . 0) (10 -963.4421111598 9.3553443461) (40 . 0.0000000000) (41 . 0.0000000000) (42 . -0.4142135624) (91 . 0) (10 -962.9421111598 8.8553443461) (40 . 0.0000000000) (41 . 0.0000000000) (42 . 0.0000000000) (91 . 0) (10 -962.9421111598 -24.1446556539) (40 . 0.0000000000) (41 . 0.0000000000) (42 . -0.4142135624) (91 . 0) (10 -963.4421111598 -24.6446556539) (40 . 0.0000000000) (41 . 0.0000000000) (42 . 0.0000000000) (91 . 0) (10 -966.6421111598 -24.6446556539) (40 . 0.0000000000) (41 . 0.0000000000) (42 . 0.4142135624) (91 . 0) (10 -967.1421111598 -25.1446556539) (40 . 0.0000000000) (41 . 0.0000000000) (42 . 0.0000000000) (91 . 0) (10 -967.1421111598 -26.1446556539) (40 . 0.0000000000) (41 . 0.0000000000) (42 . 0.4142135624) (91 . 0) (10 -966.6421111598 -26.6446556539) (40 . 0.0000000000) (41 . 0.0000000000) (42 . 0.0000000000) (91 . 0) (10 -963.4421111598 -26.6446556539) (40 . 0.0000000000) (41 . 0.0000000000) (42 . -0.4142135624) (91 . 0) (10 -962.9421111598 -27.1446556539) (40 . 0.0000000000) (41 . 0.0000000000) (42 . 0.0000000000) (91 . 0) (10 -962.9421111598 -29.1446556539) (40 . 0.0000000000) (41 . 0.0000000000) (42 . 0.4142135624) (91 . 0) (10 -962.4421111598 -29.6446556539) (40 . 0.0000000000) (41 . 0.0000000000) (42 . 0.0000000000) (91 . 0) (10 -921.4421111598 -29.6446556539) (40 . 0.0000000000) (41 . 0.0000000000) (42 . 0.4142135624) (91 . 0) (10 -920.9421111598 -29.1446556539) (40 . 0.0000000000) (41 . 0.0000000000) (42 . 0.0000000000) (91 . 0) (10 -920.9421111598 -26.1446556539) (40 . 0.0000000000) (41 . 0.0000000000) (42 . 0.4142135624) (91 . 0) (10 -921.4421111598 -25.6446556539) (40 . 0.0000000000) (41 . 0.0000000000) (42 . 0.0000000000) (91 . 0) (10 -923.1421111599 -25.6446556539) (40 . 0.0000000000) (41 . 0.0000000000) (42 . 0.4142135624) (91 . 0) (10 -923.6421111599 -26.1446556539) (40 . 0.0000000000) (41 . 0.0000000000) (42 . 0.4142135624) (91 . 0) (10 -923.1421111599 -26.6446556539) (40 . 0.0000000000) (41 . 0.0000000000) (42 . 0.0000000000) (91 . 0) (10 -922.9421111598 -26.6446556539) (40 . 0.0000000000) (41 . 0.0000000000) (42 . -0.4142135624) (91 . 0) (10 -922.4421111598 -27.1446556539) (40 . 0.0000000000) (41 . 0.0000000000) (42 . 0.0000000000) (91 . 0) (10 -922.4421111598 -27.5446556539) (40 . 0.0000000000) (41 . 0.0000000000) (42 . -0.4142135624) (91 . 0) (10 -922.9421111598 -28.0446556539) (40 . 0.0000000000) (41 . 0.0000000000) (42 . 0.0000000000) (91 . 0) (10 -927.9421111598 -28.0446556539) (40 . 0.0000000000) (41 . 0.0000000000) (42 . -0.4142135624) (91 . 0) (10 -928.4421111598 -27.5446556539) (40 . 0.0000000000) (41 . 0.0000000000) (42 . 0.0000000000) (91 . 0) (10 -928.4421111598 -27.1446556539) (40 . 0.0000000000) (41 . 0.0000000000) (42 . -0.4142135624) (91 . 0) (10 -927.9421111598 -26.6446556539) (40 . 0.0000000000) (41 . 0.0000000000) (42 . 0.0000000000) (91 . 0) (10 -927.7421111597 -26.6446556539) (40 . 0.0000000000) (41 . 0.0000000000) (42 . 0.4142135624) (91 . 0) (10 -927.2421111597 -26.1446556539) (40 . 0.0000000000) (41 . 0.0000000000) (42 . 0.0000000000) (91 . 0) (10 -927.2421111597 -26.1446556539) (40 . 0.0000000000) (41 . 0.0000000000) (42 . 0.4142135624) (91 . 0) (10 -927.7421111597 -25.6446556539) (40 . 0.0000000000) (41 . 0.0000000000) (42 . 0.0000000000) (91 . 0) (10 -929.4421111598 -25.6446556539) (40 . 0.0000000000) (41 . 0.0000000000) (42 . 0.4142135624) (91 . 0) (10 -929.9421111598 -26.1446556539) (40 . 0.0000000000) (41 . 0.0000000000) (42 . 0.0000000000) (91 . 0) (10 -929.9421111598 -27.6446556539) (40 . 0.0000000000) (41 . 0.0000000000) (42 . -0.4142135624) (91 . 0) (10 -930.4421111598 -28.1446556539) (40 . 0.0000000000) (41 . 0.0000000000) (42 . 0.0000000000) (91 . 0) (10 -952.1421111598 -28.1446556539) (40 . 0.0000000000) (41 . 0.0000000000) (42 . -0.4142135624) (91 . 0) (10 -952.6421111598 -27.6446556539) (40 . 0.0000000000) (41 . 0.0000000000) (42 . 0.0000000000) (91 . 0) (10 -952.6421111598 -4.6431837913) (40 . 0.0000000000) (41 . 0.0000000000) (42 . 0.1989123674) (91 . 0) (10 -952.7299791254 -4.4310517569) (40 . 0.0000000000) (41 . 0.0000000000) (42 . 0.0000000000) (91 . 0) (10 -953.0542431941 -4.1067876882) (40 . 0.0000000000) (41 . 0.0000000000) (42 . -0.4142135624) (91 . 0) (10 -953.0542431941 -3.6825236195) (40 . 0.0000000000) (41 . 0.0000000000) (42 . 0.0000000000) (91 . 0) (10 -952.7299791254 -3.3582595508) (40 . 0.0000000000) (41 . 0.0000000000) (42 . 0.1989123674) (91 . 0) (10 -952.6421111598 -3.1461275164) (40 . 0.0000000000) (41 . 0.0000000000) (42 . 0.0000000000) (91 . 0) (10 -952.6421111598 5.1068162087) (40 . 0.0000000000) (41 . 0.0000000000) (42 . 0.1989123674) (91 . 0) (10 -952.7299791254 5.3189482431) (40 . 0.0000000000) (41 . 0.0000000000) (42 . 0.0000000000) (91 . 0) (10 -953.0542431941 5.6432123118) (40 . 0.0000000000) (41 . 0.0000000000) (42 . -0.4142135624) (91 . 0) (10 -953.0542431941 6.0674763805) (40 . 0.0000000000) (41 . 0.0000000000) (42 . 0.0000000000) (91 . 0) (10 -952.7299791254 6.3917404492) (40 . 0.0000000000) (41 . 0.0000000000) (42 . 0.1989123674) (91 . 0) (10 -952.6421111598 6.6038724836) (40 . 0.0000000000) (41 . 0.0000000000) (42 . 0.0000000000) (91 . 0) (10 -952.6421111598 19.8553443461) (40 . 0.0000000000) (41 . 0.0000000000) (42 . 0.4142135624) (91 . 0) (10 -953.1421111598 20.3553443461) (40 . 0.0000000000) (41 . 0.0000000000) (42 . 0.0000000000) (91 . 0) (10 -966.6421111598 20.3553443461) (40 . 0.0000000000) (41 . 0.0000000000) (42 . 0.4142135624) (91 . 0) (210 0.0000000000 0.0000000000 -1.0000000000))
((0 . "LWPOLYLINE") (100 . "AcDbEntity") (67 . 0) (8 . "A-Window") (62 . 151) (6 . "Continuous") (100 . "AcDbPolyline") (90 . 24) (70 . 1) (43 . 0.0000000000) (38 . 0.0000000000) (39 . 0.0000000000) (10 -961.1421111598 -28.1446556539) (40 . 0.0000000000) (41 . 0.0000000000) (42 . -0.4142135624) (91 . 0) (10 -961.4421111598 -27.8446556539) (40 . 0.0000000000) (41 . 0.0000000000) (42 . 0.0000000000) (91 . 0) (10 -961.4421111598 15.5553443461) (40 . 0.0000000000) (41 . 0.0000000000) (42 . -0.4142135624) (91 . 0) (10 -961.1421111598 15.8553443461) (40 . 0.0000000000) (41 . 0.0000000000) (42 . 0.0000000000) (91 . 0) (10 -960.4421111598 15.8553443461) (40 . 0.0000000000) (41 . 0.0000000000) (42 . 0.4142135624) (91 . 0) (10 -959.9421111598 16.3553443461) (40 . 0.0000000000) (41 . 0.0000000000) (42 . 0.0000000000) (91 . 0) (10 -959.9421111598 16.5553443461) (40 . 0.0000000000) (41 . 0.0000000000) (42 . 0.4142135624) (91 . 0) (10 -960.4421111598 17.0553443461) (40 . 0.0000000000) (41 . 0.0000000000) (42 . 0.0000000000) (91 . 0) (10 -960.9421111598 17.0553443461) (40 . 0.0000000000) (41 . 0.0000000000) (42 . -0.4142135624) (91 . 0) (10 -961.4421111598 17.5553443461) (40 . 0.0000000000) (41 . 0.0000000000) (42 . 0.0000000000) (91 . 0) (10 -961.4421111598 18.3553443461) (40 . 0.0000000000) (41 . 0.0000000000) (42 . -0.4142135624) (91 . 0) (10 -960.9421111598 18.8553443461) (40 . 0.0000000000) (41 . 0.0000000000) (42 . 0.0000000000) (91 . 0) (10 -955.1421111598 18.8553443461) (40 . 0.0000000000) (41 . 0.0000000000) (42 . -0.4142135624) (91 . 0) (10 -954.6421111598 18.3553443461) (40 . 0.0000000000) (41 . 0.0000000000) (42 . 0.0000000000) (91 . 0) (10 -954.6421111598 17.5553443461) (40 . 0.0000000000) (41 . 0.0000000000) (42 . -0.4142135624) (91 . 0) (10 -955.1421111598 17.0553443461) (40 . 0.0000000000) (41 . 0.0000000000) (42 . 0.0000000000) (91 . 0) (10 -955.6421111598 17.0553443461) (40 . 0.0000000000) (41 . 0.0000000000) (42 . 0.4142135624) (91 . 0) (10 -956.1421111598 16.5553443461) (40 . 0.0000000000) (41 . 0.0000000000) (42 . 0.0000000000) (91 . 0) (10 -956.1421111598 16.3553443461) (40 . 0.0000000000) (41 . 0.0000000000) (42 . 0.4142135624) (91 . 0) (10 -955.6421111598 15.8553443461) (40 . 0.0000000000) (41 . 0.0000000000) (42 . 0.0000000000) (91 . 0) (10 -954.9421111598 15.8553443461) (40 . 0.0000000000) (41 . 0.0000000000) (42 . -0.4142135624) (91 . 0) (10 -954.6421111598 15.5553443461) (40 . 0.0000000000) (41 . 0.0000000000) (42 . 0.0000000000) (91 . 0) (10 -954.6421111598 -27.8446556539) (40 . 0.0000000000) (41 . 0.0000000000) (42 . -0.4142135624) (91 . 0) (10 -954.9421111598 -28.1446556539) (40 . 0.0000000000) (41 . 0.0000000000) (42 . 0.0000000000) (91 . 0) (210 0.0000000000 0.0000000000 -1.0000000000))
((0 . "LWPOLYLINE") (100 . "AcDbEntity") (67 . 0) (8 . "A-Window") (62 . 151) (6 . "Continuous") (100 . "AcDbPolyline") (90 . 27) (70 . 1) (43 . 0.0000000000) (38 . 0.0000000000) (39 . 0.0000000000) (10 -46.6343442037 26.2511348353) (40 . 0.0000000000) (41 . 0.0000000000) (42 . 0.0000000000) (91 . 0) (10 -41.6502781174 26.2576674749) (40 . 0.0000000000) (41 . 0.0000000000) (42 . 0.0000000000) (91 . 0) (10 -41.6502781174 25.4345600777) (40 . 0.0000000000) (41 . 0.0000000000) (42 . -0.4142135624) (91 . 0) (10 -41.8502781175 25.2345600777) (40 . 0.0000000000) (41 . 0.0000000000) (42 . 0.0000000000) (91 . 0) (10 -42.9292255490 25.2345600777) (40 . 0.0000000000) (41 . 0.0000000000) (42 . 0.4142135624) (91 . 0) (10 -43.1292255490 25.0345600777) (40 . 0.0000000000) (41 . 0.0000000000) (42 . 0.0000000000) (91 . 0) (10 -43.1292255490 24.3317958720) (40 . 0.0000000000) (41 . 0.0000000000) (42 . 0.4142135624) (91 . 0) (10 -42.6292255490 23.8317958720) (40 . 0.0000000000) (41 . 0.0000000000) (42 . 0.0000000000) (91 . 0) (10 -41.5395793878 23.8317958720) (40 . 0.0000000000) (41 . 0.0000000000) (42 . -0.4142135624) (91 . 0) (10 -41.0395793878 23.3317958720) (40 . 0.0000000000) (41 . 0.0000000000) (42 . 0.0000000000) (91 . 0) (10 -41.0395793878 22.4328904396) (40 . 0.0000000000) (41 . 0.0000000000) (42 . -0.1452621195) (91 . 0) (10 -41.2558473432 21.7041923178) (40 . 0.0000000000) (41 . 0.0000000000) (42 . -0.1071711367) (91 . 0) (10 -41.9812023489 20.9862582435) (40 . 0.0000000000) (41 . 0.0000000000) (42 . -0.0774042911) (91 . 0) (10 -42.9712474046 20.5533278266) (40 . 0.0000000000) (41 . 0.0000000000) (42 . -0.0645213706) (91 . 0) (10 -44.2544812721 20.3870435681) (40 . 0.0000000000) (41 . 0.0000000000) (42 . -0.0645213706) (91 . 0) (10 -45.5377151397 20.5533278266) (40 . 0.0000000000) (41 . 0.0000000000) (42 . -0.0774042911) (91 . 0) (10 -46.5277601954 20.9862582435) (40 . 0.0000000000) (41 . 0.0000000000) (42 . -0.1071711367) (91 . 0) (10 -47.2531152011 21.7041923178) (40 . 0.0000000000) (41 . 0.0000000000) (42 . -0.1452621195) (91 . 0) (10 -47.4693831565 22.4328904396) (40 . 0.0000000000) (41 . 0.0000000000) (42 . 0.0000000000) (91 . 0) (10 -47.4693831565 23.3317958720) (40 . 0.0000000000) (41 . 0.0000000000) (42 . -0.4142135624) (91 . 0) (10 -46.9693831565 23.8317958720) (40 . 0.0000000000) (41 . 0.0000000000) (42 . 0.0000000000) (91 . 0) (10 -45.6292255489 23.8317958720) (40 . 0.0000000000) (41 . 0.0000000000) (42 . 0.4142135624) (91 . 0) (10 -45.1292255490 24.3317958720) (40 . 0.0000000000) (41 . 0.0000000000) (42 . 0.0000000000) (91 . 0) (10 -45.1292255490 25.0345600777) (40 . 0.0000000000) (41 . 0.0000000000) (42 . 0.4142135624) (91 . 0) (10 -45.3292255489 25.2345600777) (40 . 0.0000000000) (41 . 0.0000000000) (42 . 0.0000000000) (91 . 0) (10 -46.4343442038 25.2345600777) (40 . 0.0000000000) (41 . 0.0000000000) (42 . -0.4142135624) (91 . 0) (10 -46.6343442037 25.4345600777) (40 . 0.0000000000) (41 . 0.0000000000) (42 . 0.0000000000) (91 . 0) (210 0.0000000000 0.0000000000 -1.0000000000))
((0 . "LWPOLYLINE") (100 . "AcDbEntity") (67 . 0) (8 . "A-Window") (62 . 151) (6 . "Continuous") (370 . -3) (100 . "AcDbPolyline") (90 . 21) (70 . 1) (43 . 0.0000000000) (38 . 0.0000000000) (39 . 0.0000000000) (10 -46.9693831565 22.4328904396) (40 . 0.0000000000) (41 . 0.0000000000) (42 . 0.1452621195) (91 . 0) (10 -46.8340671429 21.9769536143) (40 . 0.0000000000) (41 . 0.0000000000) (42 . 0.1071711367) (91 . 0) (10 -46.2593224290 21.4080889744) (40 . 0.0000000000) (41 . 0.0000000000) (42 . 0.0774042911) (91 . 0) (10 -45.4102728990 21.0368135815) (40 . 0.0000000000) (41 . 0.0000000000) (42 . 0.0645213706) (91 . 0) (10 -44.2544812721 20.8870435681) (40 . 0.0000000000) (41 . 0.0000000000) (42 . 0.0645213706) (91 . 0) (10 -43.0986896453 21.0368135815) (40 . 0.0000000000) (41 . 0.0000000000) (42 . 0.0774042911) (91 . 0) (10 -42.2496401153 21.4080889744) (40 . 0.0000000000) (41 . 0.0000000000) (42 . 0.1071711367) (91 . 0) (10 -41.6748954014 21.9769536143) (40 . 0.0000000000) (41 . 0.0000000000) (42 . 0.1452621195) (91 . 0) (10 -41.5395793877 22.4328904396) (40 . 0.0000000000) (41 . 0.0000000000) (42 . 0.0000000000) (91 . 0) (10 -41.5395793877 22.8345600779) (40 . 0.0000000000) (41 . 0.0000000000) (42 . 0.4142135624) (91 . 0) (10 -42.0395793877 23.3345600779) (40 . 0.0000000000) (41 . 0.0000000000) (42 . 0.0000000000) (91 . 0) (10 -43.2879351591 23.3345600779) (40 . 0.0000000000) (41 . 0.0000000000) (42 . -0.3939487093) (91 . 0) (10 -43.7867217974 23.7997478752) (40 . 0.0000000000) (41 . 0.0000000000) (42 . 0.0000000000) (91 . 0) (10 -43.8738758732 25.0484849588) (40 . 0.0000000000) (41 . 0.0000000000) (42 . 0.3939487093) (91 . 0) (10 -44.0733905285 25.2345600777) (40 . 0.0000000000) (41 . 0.0000000000) (42 . 0.0000000000) (91 . 0) (10 -44.2020517470 25.2345600777) (40 . 0.0000000000) (41 . 0.0000000000) (42 . 0.3852515762) (91 . 0) (10 -44.4010548823 25.0545038025) (40 . 0.0000000000) (41 . 0.0000000000) (42 . 0.0000000000) (91 . 0) (10 -44.5283121857 23.7847007658) (40 . 0.0000000000) (41 . 0.0000000000) (42 . -0.3852515762) (91 . 0) (10 -45.0258200238 23.3345600779) (40 . 0.0000000000) (41 . 0.0000000000) (42 . 0.0000000000) (91 . 0) (10 -46.4693831565 23.3345600779) (40 . 0.0000000000) (41 . 0.0000000000) (42 . 0.4142135624) (91 . 0) (10 -46.9693831565 22.8345600779) (40 . 0.0000000000) (41 . 0.0000000000) (42 . 0.0000000000) (91 . 0) (210 0.0000000000 0.0000000000 -1.0000000000))
((0 . "LWPOLYLINE") (100 . "AcDbEntity") (67 . 0) (8 . "A-Window") (62 . 151) (6 . "Continuous") (100 . "AcDbPolyline") (90 . 27) (70 . 1) (43 . 0.0000000000) (38 . 0.0000000000) (39 . 0.0000000000) (10 -41.6502781188 26.2512293333) (40 . 0.0000000000) (41 . 0.0000000000) (42 . 0.0000000000) (91 . 0) (10 -46.6343442023 26.2577619728) (40 . 0.0000000000) (41 . 0.0000000000) (42 . 0.0000000000) (91 . 0) (10 -46.6343442023 25.4346545761) (40 . 0.0000000000) (41 . 0.0000000000) (42 . 0.4142135624) (91 . 0) (10 -46.4343442025 25.2346545762) (40 . 0.0000000000) (41 . 0.0000000000) (42 . 0.0000000000) (91 . 0) (10 -45.3553967715 25.2346545762) (40 . 0.0000000000) (41 . 0.0000000000) (42 . -0.4142135624) (91 . 0) (10 -45.1553967716 25.0346545763) (40 . 0.0000000000) (41 . 0.0000000000) (42 . 0.0000000000) (91 . 0) (10 -45.1553967716 24.3318903710) (40 . 0.0000000000) (41 . 0.0000000000) (42 . -0.4142135624) (91 . 0) (10 -45.6553967713 23.8318903713) (40 . 0.0000000000) (41 . 0.0000000000) (42 . 0.0000000000) (91 . 0) (10 -46.7450429320 23.8318903713) (40 . 0.0000000000) (41 . 0.0000000000) (42 . 0.4142135624) (91 . 0) (10 -47.2450429317 23.3318903716) (40 . 0.0000000000) (41 . 0.0000000000) (42 . 0.0000000000) (91 . 0) (10 -47.2450429317 22.4329849397) (40 . 0.0000000000) (41 . 0.0000000000) (42 . 0.1452621195) (91 . 0) (10 -47.0287749764 21.7042868183) (40 . 0.0000000000) (41 . 0.0000000000) (42 . 0.1071711367) (91 . 0) (10 -46.3034199711 20.9863527444) (40 . 0.0000000000) (41 . 0.0000000000) (42 . 0.0774042911) (91 . 0) (10 -45.3133749159 20.5534223277) (40 . 0.0000000000) (41 . 0.0000000000) (42 . 0.0645213706) (91 . 0) (10 -44.0301410491 20.3871380694) (40 . 0.0000000000) (41 . 0.0000000000) (42 . 0.0645213706) (91 . 0) (10 -42.7469071823 20.5534223277) (40 . 0.0000000000) (41 . 0.0000000000) (42 . 0.0774042911) (91 . 0) (10 -41.7568621271 20.9863527444) (40 . 0.0000000000) (41 . 0.0000000000) (42 . 0.1071711367) (91 . 0) (10 -41.0315071219 21.7042868183) (40 . 0.0000000000) (41 . 0.0000000000) (42 . 0.1452621195) (91 . 0) (10 -40.8152391666 22.4329849397) (40 . 0.0000000000) (41 . 0.0000000000) (42 . 0.0000000000) (91 . 0) (10 -40.8152391666 23.3318903716) (40 . 0.0000000000) (41 . 0.0000000000) (42 . 0.4142135624) (91 . 0) (10 -41.3152391663 23.8318903713) (40 . 0.0000000000) (41 . 0.0000000000) (42 . 0.0000000000) (91 . 0) (10 -42.6553967731 23.8318903713) (40 . 0.0000000000) (41 . 0.0000000000) (42 . -0.4142135624) (91 . 0) (10 -43.1553967728 24.3318903710) (40 . 0.0000000000) (41 . 0.0000000000) (42 . 0.0000000000) (91 . 0) (10 -43.1553967728 25.0346545763) (40 . 0.0000000000) (41 . 0.0000000000) (42 . -0.4142135624) (91 . 0) (10 -42.9553967729 25.2346545762) (40 . 0.0000000000) (41 . 0.0000000000) (42 . 0.0000000000) (91 . 0) (10 -41.8502781187 25.2346545762) (40 . 0.0000000000) (41 . 0.0000000000) (42 . 0.4142135624) (91 . 0) (10 -41.6502781188 25.4346545761) (40 . 0.0000000000) (41 . 0.0000000000) (42 . 0.0000000000) (91 . 0) (210 0.0000000000 0.0000000000 -1.0000000000))
((0 . "LWPOLYLINE") (100 . "AcDbEntity") (67 . 0) (8 . "A-Window") (62 . 151) (6 . "Continuous") (370 . -3) (100 . "AcDbPolyline") (90 . 21) (70 . 1) (43 . 0.0000000000) (38 . 0.0000000000) (39 . 0.0000000000) (10 -41.3152391662 22.4329849397) (40 . 0.0000000000) (41 . 0.0000000000) (42 . -0.1452621195) (91 . 0) (10 -41.4505551798 21.9770481146) (40 . 0.0000000000) (41 . 0.0000000000) (42 . -0.1071711367) (91 . 0) (10 -42.0252998934 21.4081834751) (40 . 0.0000000000) (41 . 0.0000000000) (42 . -0.0774042911) (91 . 0) (10 -42.8743494229 21.0369080824) (40 . 0.0000000000) (41 . 0.0000000000) (42 . -0.0645213706) (91 . 0) (10 -44.0301410491 20.8871380690) (40 . 0.0000000000) (41 . 0.0000000000) (42 . -0.0645213706) (91 . 0) (10 -45.1859326753 21.0369080824) (40 . 0.0000000000) (41 . 0.0000000000) (42 . -0.0774042911) (91 . 0) (10 -46.0349822049 21.4081834751) (40 . 0.0000000000) (41 . 0.0000000000) (42 . -0.1071711367) (91 . 0) (10 -46.6097269184 21.9770481146) (40 . 0.0000000000) (41 . 0.0000000000) (42 . -0.1452621195) (91 . 0) (10 -46.7450429320 22.4329849397) (40 . 0.0000000000) (41 . 0.0000000000) (42 . 0.0000000000) (91 . 0) (10 -46.7450429320 22.8346545778) (40 . 0.0000000000) (41 . 0.0000000000) (42 . -0.4142135624) (91 . 0) (10 -46.2450429323 23.3346545775) (40 . 0.0000000000) (41 . 0.0000000000) (42 . 0.0000000000) (91 . 0) (10 -44.9966871616 23.3346545775) (40 . 0.0000000000) (41 . 0.0000000000) (42 . 0.3939487093) (91 . 0) (10 -44.4979005236 23.7998423745) (40 . 0.0000000000) (41 . 0.0000000000) (42 . 0.0000000000) (91 . 0) (10 -44.4107464478 25.0485794574) (40 . 0.0000000000) (41 . 0.0000000000) (42 . -0.3939487093) (91 . 0) (10 -44.2112317927 25.2346545762) (40 . 0.0000000000) (41 . 0.0000000000) (42 . 0.0000000000) (91 . 0) (10 -44.0825705742 25.2346545762) (40 . 0.0000000000) (41 . 0.0000000000) (42 . -0.3852515762) (91 . 0) (10 -43.8835674391 25.0545983012) (40 . 0.0000000000) (41 . 0.0000000000) (42 . 0.0000000000) (91 . 0) (10 -43.7563101358 23.7847952652) (40 . 0.0000000000) (41 . 0.0000000000) (42 . 0.3852515762) (91 . 0) (10 -43.2588022979 23.3346545775) (40 . 0.0000000000) (41 . 0.0000000000) (42 . 0.0000000000) (91 . 0) (10 -41.8152391660 23.3346545775) (40 . 0.0000000000) (41 . 0.0000000000) (42 . -0.4142135624) (91 . 0) (10 -41.3152391662 22.8346545778) (40 . 0.0000000000) (41 . 0.0000000000) (42 . 0.0000000000) (91 . 0) (210 0.0000000000 0.0000000000 -1.0000000000))
((0 . "LWPOLYLINE") (100 . "AcDbEntity") (67 . 0) (8 . "A-Window") (62 . 151) (6 . "Continuous") (100 . "AcDbPolyline") (90 . 28) (70 . 1) (43 . 0.0000000000) (38 . 0.0000000000) (39 . 0.0000000000) (10 -76.1421111606 23.0553443463) (40 . 0.0000000000) (41 . 0.0000000000) (42 . 0.0000000000) (91 . 0) (10 -76.1421111606 -20.3446556537) (40 . 0.0000000000) (41 . 0.0000000000) (42 . 0.4142135624) (91 . 0) (10 -75.8421111606 -20.6446556537) (40 . 0.0000000000) (41 . 0.0000000000) (42 . 0.0000000000) (91 . 0) (10 -69.6421111606 -20.6446556537) (40 . 0.0000000000) (41 . 0.0000000000) (42 . 0.4142135624) (91 . 0) (10 -69.3421111606 -20.3446556537) (40 . 0.0000000000) (41 . 0.0000000000) (42 . 0.0000000000) (91 . 0) (10 -69.3421111606 3.1553443463) (40 . 0.0000000000) (41 . 0.0000000000) (42 . -0.4142135624) (91 . 0) (10 -68.3421111606 4.1553443463) (40 . 0.0000000000) (41 . 0.0000000000) (42 . 0.0000000000) (91 . 0) (10 -66.6421111606 4.1553443463) (40 . 0.0000000000) (41 . 0.0000000000) (42 . 0.4142135624) (91 . 0) (10 -66.1421111606 4.6553443463) (40 . 0.0000000000) (41 . 0.0000000000) (42 . 0.0000000000) (91 . 0) (10 -66.1421111606 7.3553443463) (40 . 0.0000000000) (41 . 0.0000000000) (42 . 0.4142135624) (91 . 0) (10 -66.6421111606 7.8553443463) (40 . 0.0000000000) (41 . 0.0000000000) (42 . 0.0000000000) (91 . 0) (10 -68.3421111606 7.8553443463) (40 . 0.0000000000) (41 . 0.0000000000) (42 . -0.4142135624) (91 . 0) (10 -69.3421111606 8.8553443463) (40 . 0.0000000000) (41 . 0.0000000000) (42 . 0.0000000000) (91 . 0) (10 -69.3421111606 18.8553443463) (40 . 0.0000000000) (41 . 0.0000000000) (42 . -0.4142135624) (91 . 0) (10 -68.3421111606 19.8553443463) (40 . 0.0000000000) (41 . 0.0000000000) (42 . 0.0000000000) (91 . 0) (10 -65.6421111606 19.8553443463) (40 . 0.0000000000) (41 . 0.0000000000) (42 . 0.4142135624) (91 . 0) (10 -65.1421111606 20.3553443463) (40 . 0.0000000000) (41 . 0.0000000000) (42 . 0.0000000000) (91 . 0) (10 -65.1421111606 28.8553443463) (40 . 0.0000000000) (41 . 0.0000000000) (42 . 0.4142135624) (91 . 0) (10 -65.6421111606 29.3553443463) (40 . 0.0000000000) (41 . 0.0000000000) (42 . 0.0000000000) (91 . 0) (10 -75.6421111606 29.3553443463) (40 . 0.0000000000) (41 . 0.0000000000) (42 . 0.4142135624) (91 . 0) (10 -76.1421111606 28.8553443463) (40 . 0.0000000000) (41 . 0.0000000000) (42 . 0.0000000000) (91 . 0) (10 -76.1421111606 25.3553443463) (40 . 0.0000000000) (41 . 0.0000000000) (42 . 0.4142135624) (91 . 0) (10 -75.6421111606 24.8553443463) (40 . 0.0000000000) (41 . 0.0000000000) (42 . 0.0000000000) (91 . 0) (10 -75.1421111606 24.8553443463) (40 . 0.0000000000) (41 . 0.0000000000) (42 . -0.4142135624) (91 . 0) (10 -74.6421111606 24.3553443463) (40 . 0.0000000000) (41 . 0.0000000000) (42 . 0.0000000000) (91 . 0) (10 -74.6421111606 23.8553443463) (40 . 0.0000000000) (41 . 0.0000000000) (42 . -0.4142135624) (91 . 0) (10 -75.1421111606 23.3553443463) (40 . 0.0000000000) (41 . 0.0000000000) (42 . 0.0000000000) (91 . 0) (10 -75.8421111606 23.3553443463) (40 . 0.0000000000) (41 . 0.0000000000) (42 . 0.4142135624) (91 . 0) (210 0.0000000000 0.0000000000 -1.0000000000))
((0 . "LWPOLYLINE") (100 . "AcDbEntity") (67 . 0) (8 . "A-Window") (62 . 151) (6 . "Continuous") (100 . "AcDbPolyline") (90 . 71) (70 . 1) (43 . 0.0000000000) (38 . 0.0000000000) (39 . 0.0000000000) (10 -51.4421111606 29.0553443463) (40 . 0.0000000000) (41 . 0.0000000000) (42 . 0.0000000000) (91 . 0) (10 -51.4421111606 27.3553443463) (40 . 0.0000000000) (41 . 0.0000000000) (42 . -0.4142135624) (91 . 0) (10 -51.9421111606 26.8553443463) (40 . 0.0000000000) (41 . 0.0000000000) (42 . 0.0000000000) (91 . 0) (10 -54.1421111606 26.8553443463) (40 . 0.0000000000) (41 . 0.0000000000) (42 . -0.4142135624) (91 . 0) (10 -54.4421111606 27.1553443463) (40 . 0.0000000000) (41 . 0.0000000000) (42 . 0.0000000000) (91 . 0) (10 -54.4421111606 27.5553443463) (40 . 0.0000000000) (41 . 0.0000000000) (42 . -0.4142135624) (91 . 0) (10 -54.1421111606 27.8553443463) (40 . 0.0000000000) (41 . 0.0000000000) (42 . 0.0000000000) (91 . 0) (10 -53.2421111606 27.8553443463) (40 . 0.0000000000) (41 . 0.0000000000) (42 . 0.4142135624) (91 . 0) (10 -52.9421111606 28.1553443463) (40 . 0.0000000000) (41 . 0.0000000000) (42 . 0.0000000000) (91 . 0) (10 -52.9421111606 29.0553443463) (40 . 0.0000000000) (41 . 0.0000000000) (42 . 0.4142135624) (91 . 0) (10 -53.2421111606 29.3553443463) (40 . 0.0000000000) (41 . 0.0000000000) (42 . 0.0000000000) (91 . 0) (10 -63.1421111606 29.3553443463) (40 . 0.0000000000) (41 . 0.0000000000) (42 . 0.4142135624) (91 . 0) (10 -63.6421111606 28.8553443463) (40 . 0.0000000000) (41 . 0.0000000000) (42 . 0.0000000000) (91 . 0) (10 -63.6421111606 18.8553443463) (40 . 0.0000000000) (41 . 0.0000000000) (42 . -0.4142135624) (91 . 0) (10 -64.1421111606 18.3553443463) (40 . 0.0000000000) (41 . 0.0000000000) (42 . 0.0000000000) (91 . 0) (10 -67.3421111606 18.3553443463) (40 . 0.0000000000) (41 . 0.0000000000) (42 . 0.4142135624) (91 . 0) (10 -67.8421111606 17.8553443463) (40 . 0.0000000000) (41 . 0.0000000000) (42 . 0.0000000000) (91 . 0) (10 -67.8421111606 9.8553443463) (40 . 0.0000000000) (41 . 0.0000000000) (42 . 0.4142135624) (91 . 0) (10 -67.3421111606 9.3553443463) (40 . 0.0000000000) (41 . 0.0000000000) (42 . 0.0000000000) (91 . 0) (10 -65.3421111606 9.3553443463) (40 . 0.0000000000) (41 . 0.0000000000) (42 . 0.4142135624) (91 . 0) (10 -64.8421111606 9.8553443463) (40 . 0.0000000000) (41 . 0.0000000000) (42 . 0.0000000000) (91 . 0) (10 -64.8421111606 11.6553443463) (40 . 0.0000000000) (41 . 0.0000000000) (42 . -0.4142135624) (91 . 0) (10 -64.3421111606 12.1553443463) (40 . 0.0000000000) (41 . 0.0000000000) (42 . 0.0000000000) (91 . 0) (10 -64.1421111606 12.1553443463) (40 . 0.0000000000) (41 . 0.0000000000) (42 . -0.4142135624) (91 . 0) (10 -63.6421111606 11.6553443463) (40 . 0.0000000000) (41 . 0.0000000000) (42 . 0.0000000000) (91 . 0) (10 -63.6421111606 6.6867151962) (40 . 0.0000000000) (41 . 0.0000000000) (42 . -0.1989123674) (91 . 0) (10 -63.7885577700 6.3331618056) (40 . 0.0000000000) (41 . 0.0000000000) (42 . 0.0000000000) (91 . 0) (10 -64.0542431949 6.0674763807) (40 . 0.0000000000) (41 . 0.0000000000) (42 . 0.4142135624) (91 . 0) (10 -64.0542431949 5.6432123120) (40 . 0.0000000000) (41 . 0.0000000000) (42 . 0.0000000000) (91 . 0) (10 -63.7885577700 5.3775268870) (40 . 0.0000000000) (41 . 0.0000000000) (42 . -0.1989123674) (91 . 0) (10 -63.6421111606 5.0239734964) (40 . 0.0000000000) (41 . 0.0000000000) (42 . 0.0000000000) (91 . 0) (10 -63.6421111606 0.3553443463) (40 . 0.0000000000) (41 . 0.0000000000) (42 . -0.4142135624) (91 . 0) (10 -64.1421111606 -0.1446556537) (40 . 0.0000000000) (41 . 0.0000000000) (42 . 0.0000000000) (91 . 0) (10 -64.3421111606 -0.1446556537) (40 . 0.0000000000) (41 . 0.0000000000) (42 . -0.4142135624) (91 . 0) (10 -64.8421111606 0.3553443463) (40 . 0.0000000000) (41 . 0.0000000000) (42 . 0.0000000000) (91 . 0) (10 -64.8421111606 2.1553443463) (40 . 0.0000000000) (41 . 0.0000000000) (42 . 0.4142135624) (91 . 0) (10 -65.3421111606 2.6553443463) (40 . 0.0000000000) (41 . 0.0000000000) (42 . 0.0000000000) (91 . 0) (10 -67.3421111606 2.6553443463) (40 . 0.0000000000) (41 . 0.0000000000) (42 . 0.4142135624) (91 . 0) (10 -67.8421111606 2.1553443463) (40 . 0.0000000000) (41 . 0.0000000000) (42 . 0.0000000000) (91 . 0) (10 -67.8421111606 -6.8132848038) (40 . 0.0000000000) (41 . 0.0000000000) (42 . -0.1989123674) (91 . 0) (10 -67.9885577700 -7.1668381944) (40 . 0.0000000000) (41 . 0.0000000000) (42 . 0.0000000000) (91 . 0) (10 -68.2542431949 -7.4325236193) (40 . 0.0000000000) (41 . 0.0000000000) (42 . 0.4142135624) (91 . 0) (10 -68.2542431949 -7.8567876880) (40 . 0.0000000000) (41 . 0.0000000000) (42 . 0.0000000000) (91 . 0) (10 -67.9885577700 -8.1224731130) (40 . 0.0000000000) (41 . 0.0000000000) (42 . -0.1989123674) (91 . 0) (10 -67.8421111606 -8.4760265036) (40 . 0.0000000000) (41 . 0.0000000000) (42 . 0.0000000000) (91 . 0) (10 -67.8421111606 -20.1446556537) (40 . 0.0000000000) (41 . 0.0000000000) (42 . 0.4142135624) (91 . 0) (10 -67.3421111606 -20.6446556537) (40 . 0.0000000000) (41 . 0.0000000000) (42 . 0.0000000000) (91 . 0) (10 -65.3421111606 -20.6446556537) (40 . 0.0000000000) (41 . 0.0000000000) (42 . 0.4142135624) (91 . 0) (10 -64.8421111606 -20.1446556537) (40 . 0.0000000000) (41 . 0.0000000000) (42 . 0.0000000000) (91 . 0) (10 -64.8421111606 -15.6446556537) (40 . 0.0000000000) (41 . 0.0000000000) (42 . -0.4142135624) (91 . 0) (10 -64.3421111606 -15.1446556537) (40 . 0.0000000000) (41 . 0.0000000000) (42 . 0.0000000000) (91 . 0) (10 -64.1421111606 -15.1446556537) (40 . 0.0000000000) (41 . 0.0000000000) (42 . -0.4142135624) (91 . 0) (10 -63.6421111606 -15.6446556537) (40 . 0.0000000000) (41 . 0.0000000000) (42 . 0.0000000000) (91 . 0) (10 -63.6421111606 -21.6446556537) (40 . 0.0000000000) (41 . 0.0000000000) (42 . -0.4142135624) (91 . 0) (10 -64.1421111606 -22.1446556537) (40 . 0.0000000000) (41 . 0.0000000000) (42 . 0.0000000000) (91 . 0) (10 -80.3421111606 -22.1446556537) (40 . 0.0000000000) (41 . 0.0000000000) (42 . -0.4142135624) (91 . 0) (10 -80.8421111606 -21.6446556537) (40 . 0.0000000000) (41 . 0.0000000000) (42 . 0.0000000000) (91 . 0) (10 -80.8421111606 -19.7446556537) (40 . 0.0000000000) (41 . 0.0000000000) (42 . -0.4142135624) (91 . 0) (10 -80.3421111606 -19.2446556537) (40 . 0.0000000000) (41 . 0.0000000000) (42 . 0.0000000000) (91 . 0) (10 -78.1421111606 -19.2446556537) (40 . 0.0000000000) (41 . 0.0000000000) (42 . 0.4142135624) (91 . 0) (10 -77.6421111606 -18.7446556537) (40 . 0.0000000000) (41 . 0.0000000000) (42 . 0.0000000000) (91 . 0) (10 -77.6421111606 34.3553443463) (40 . 0.0000000000) (41 . 0.0000000000) (42 . -0.4142135624) (91 . 0) (10 -77.1421111606 34.8553443463) (40 . 0.0000000000) (41 . 0.0000000000) (42 . -0.4142135624) (91 . 0) (10 -76.6421111606 34.3553443463) (40 . 0.0000000000) (41 . 0.0000000000) (42 . 0.0000000000) (91 . 0) (10 -76.6421111606 31.3553443463) (40 . 0.0000000000) (41 . 0.0000000000) (42 . 0.4142135624) (91 . 0) (10 -76.1421111606 30.8553443463) (40 . 0.0000000000) (41 . 0.0000000000) (42 . 0.0000000000) (91 . 0) (10 -47.1421111606 30.8553443463) (40 . 0.0000000000) (41 . 0.0000000000) (42 . -0.4142135624) (91 . 0) (10 -46.6421111606 30.3553443463) (40 . 0.0000000000) (41 . 0.0000000000) (42 . 0.0000000000) (91 . 0) (10 -46.6421111606 29.8553443463) (40 . 0.0000000000) (41 . 0.0000000000) (42 . -0.4142135624) (91 . 0) (10 -47.1421111606 29.3553443463) (40 . 0.0000000000) (41 . 0.0000000000) (42 . 0.0000000000) (91 . 0) (10 -51.1421111606 29.3553443463) (40 . 0.0000000000) (41 . 0.0000000000) (42 . 0.4142135624) (91 . 0) (210 0.0000000000 0.0000000000 -1.0000000000))
((0 . "LINE") (100 . "AcDbEntity") (67 . 0) (8 . "A-Window") (62 . 6) (6 . "Continuous") (100 . "AcDbLine") (10 94.3457885244 43.0415554178 0.0000000000) (11 46.6421111606 43.0415554178 0.0000000000) (210 0.0000000000 0.0000000000 1.0000000000))
((0 . "LINE") (100 . "AcDbEntity") (67 . 0) (8 . "A-Window") (62 . 6) (6 . "Continuous") (100 . "AcDbLine") (10 94.3457885244 47.0415554178 0.0000000000) (11 46.6421111606 47.0415554178 0.0000000000) (210 0.0000000000 0.0000000000 1.0000000000))
((0 . "LWPOLYLINE") (100 . "AcDbEntity") (67 . 0) (8 . "A-Window") (62 . 151) (6 . "Continuous") (100 . "AcDbPolyline") (90 . 6) (70 . 0) (43 . 0.0000000000) (38 . 0.0000000000) (39 . 0.0000000000) (10 -94.3457885244 42.0415554178) (40 . 0.0000000000) (41 . 0.0000000000) (42 . 0.0000000000) (91 . 0) (10 -47.6421111606 42.0415554178) (40 . 0.0000000000) (41 . 0.0000000000) (42 . 0.0000000000) (91 . 0) (10 -46.6421111606 43.0415554178) (40 . 0.0000000000) (41 . 0.0000000000) (42 . 0.0000000000) (91 . 0) (10 -46.6421111606 47.0415554178) (40 . 0.0000000000) (41 . 0.0000000000) (42 . 0.0000000000) (91 . 0) (10 -47.6421111606 48.0415554178) (40 . 0.0000000000) (41 . 0.0000000000) (42 . 0.0000000000) (91 . 0) (10 -94.3457885244 48.0415554178) (40 . 0.0000000000) (41 . 0.0000000000) (42 . 0.0000000000) (91 . 0) (210 0.0000000000 0.0000000000 -1.0000000000))
((0 . "LWPOLYLINE") (100 . "AcDbEntity") (67 . 0) (8 . "A-Window") (62 . 151) (6 . "Continuous") (100 . "AcDbPolyline") (90 . 6) (70 . 0) (43 . 0.0000000000) (38 . 0.0000000000) (39 . 0.0000000000) (10 -94.3457885489 62.8553443463) (40 . 0.0000000000) (41 . 0.0000000000) (42 . 0.0000000000) (91 . 0) (10 -47.6421111606 62.8553443463) (40 . 0.0000000000) (41 . 0.0000000000) (42 . 0.0000000000) (91 . 0) (10 -46.6421111606 61.8553443463) (40 . 0.0000000000) (41 . 0.0000000000) (42 . 0.0000000000) (91 . 0) (10 -46.6421111606 57.8553443463) (40 . 0.0000000000) (41 . 0.0000000000) (42 . 0.0000000000) (91 . 0) (10 -47.6421111606 56.8553443463) (40 . 0.0000000000) (41 . 0.0000000000) (42 . 0.0000000000) (91 . 0) (10 -94.3457885489 56.8553443463) (40 . 0.0000000000) (41 . 0.0000000000) (42 . 0.0000000000) (91 . 0) (210 0.0000000000 0.0000000000 -1.0000000000))
((0 . "LINE") (100 . "AcDbEntity") (67 . 0) (8 . "A-Window") (62 . 6) (6 . "Continuous") (100 . "AcDbLine") (10 94.3457885489 57.8553443463 0.0000000000) (11 46.6421111606 57.8553443463 0.0000000000) (210 0.0000000000 0.0000000000 1.0000000000))
((0 . "LINE") (100 . "AcDbEntity") (67 . 0) (8 . "A-Window") (62 . 6) (6 . "Continuous") (100 . "AcDbLine") (10 94.3457885489 61.8549580746 0.0000000000) (11 46.6421111606 61.8549580746 0.0000000000) (210 0.0000000000 0.0000000000 1.0000000000))
((0 . "LINE") (100 . "AcDbEntity") (67 . 0) (8 . "A-Window") (62 . 151) (6 . "Continuous") (100 . "AcDbLine") (10 76.6421111606 30.8553443463 0.0000000000) (11 76.6421111605 38.8553443465 0.0000000000) (210 0.0000000000 0.0000000000 1.0000000000))
((0 . "LINE") (100 . "AcDbEntity") (67 . 0) (8 . "A-Window") (62 . 151) (6 . "Continuous") (100 . "AcDbLine") (10 60.6421111606 30.8553443463 0.0000000000) (11 76.6421111605 38.8553443465 0.0000000000) (210 0.0000000000 0.0000000000 1.0000000000))
((0 . "LINE") (100 . "AcDbEntity") (67 . 0) (8 . "A-Window") (62 . 151) (6 . "Continuous") (100 . "AcDbLine") (10 60.6421111606 38.8553443463 0.0000000000) (11 76.6421111606 30.8553443463 0.0000000000) (210 0.0000000000 0.0000000000 1.0000000000))
((0 . "LINE") (100 . "AcDbEntity") (67 . 0) (8 . "A-Window") (62 . 151) (6 . "Continuous") (100 . "AcDbLine") (10 76.6421111605 42.0415554180 0.0000000000) (11 46.6716341198 42.0415554178 0.0000000000) (210 0.0000000000 0.0000000000 1.0000000000))
((0 . "LINE") (100 . "AcDbEntity") (67 . 0) (8 . "A-Window") (62 . 151) (6 . "Continuous") (100 . "AcDbLine") (10 47.3291721178 30.8553443463 0.0000000000) (11 76.6421111606 30.8553443463 0.0000000000) (210 0.0000000000 0.0000000000 1.0000000000))
((0 . "LWPOLYLINE") (100 . "AcDbEntity") (67 . 0) (8 . "A-Window") (62 . 3) (6 . "Continuous") (100 . "AcDbPolyline") (90 . 44) (70 . 1) (43 . 0.0000000000) (38 . 0.0000000000) (39 . 0.0000000000) (10 -37.4460771165 61.7129045680) (40 . 0.0000000000) (41 . 0.0000000000) (42 . 0.0441616864) (91 . 0) (10 -30.6857113167 62.3258471634) (40 . 0.0000000000) (41 . 0.0000000000) (42 . 0.9363619320) (91 . 0) (10 -30.9254531015 63.0283855082) (40 . 0.0000000000) (41 . 0.0000000000) (42 . -0.0548443031) (91 . 0) (10 -37.2539442396 63.1010962819) (40 . 0.0000000000) (41 . 0.0000000000) (42 . 0.0302761843) (91 . 0) (10 -37.3143303468 63.1047561586) (40 . 0.0000000000) (41 . 0.0000000000) (42 . 0.0000000000) (91 . 0) (10 -44.2559511346 63.1047561586) (40 . 0.0000000000) (41 . 0.0000000000) (42 . 0.4142135624) (91 . 0) (10 -44.7559511346 62.6047561586) (40 . 0.0000000000) (41 . 0.0000000000) (42 . 0.0000000000) (91 . 0) (10 -44.7559511346 59.4047561586) (40 . 0.0000000000) (41 . 0.0000000000) (42 . 1.0000000000) (91 . 0) (10 -43.7559511346 59.4047561586) (40 . 0.0000000000) (41 . 0.0000000000) (42 . 0.0000000000) (91 . 0) (10 -43.7559511346 61.4047561586) (40 . 0.0000000000) (41 . 0.0000000000) (42 . -0.4142135624) (91 . 0) (10 -43.2559511346 61.9047561586) (40 . 0.0000000000) (41 . 0.0000000000) (42 . 0.0000000000) (91 . 0) (10 -39.4450002034 61.9047561586) (40 . 0.0000000000) (41 . 0.0000000000) (42 . -0.4142135624) (91 . 0) (10 -39.1450002034 61.6047561586) (40 . 0.0000000000) (41 . 0.0000000000) (42 . 0.0000000000) (91 . 0) (10 -39.1450002034 58.3553443462) (40 . 0.0000000000) (41 . 0.0000000000) (42 . -0.4142135624) (91 . 0) (10 -39.3450002035 58.1553443462) (40 . 0.0000000000) (41 . 0.0000000000) (42 . 0.0000000000) (91 . 0) (10 -40.3450002034 58.1553443464) (40 . 0.0000000000) (41 . 0.0000000000) (42 . -0.4142135623) (91 . 0) (10 -40.5450002034 58.3553443464) (40 . 0.0000000000) (41 . 0.0000000000) (42 . 0.0000000000) (91 . 0) (10 -40.5450002034 59.9053443463) (40 . 0.0000000000) (41 . 0.0000000000) (42 . 0.4142135624) (91 . 0) (10 -41.0450002034 60.4053443463) (40 . 0.0000000000) (41 . 0.0000000000) (42 . 0.0000000000) (91 . 0) (10 -41.4450002034 60.4053443463) (40 . 0.0000000000) (41 . 0.0000000000) (42 . 0.4142135624) (91 . 0) (10 -41.9450002034 59.9053443463) (40 . 0.0000000000) (41 . 0.0000000000) (42 . 0.0000000000) (91 . 0) (10 -41.9450002034 53.9053443463) (40 . 0.0000000000) (41 . 0.0000000000) (42 . 0.4142135624) (91 . 0) (10 -41.4450002034 53.4053443463) (40 . 0.0000000000) (41 . 0.0000000000) (42 . 0.0000000000) (91 . 0) (10 -41.0450002034 53.4053443463) (40 . 0.0000000000) (41 . 0.0000000000) (42 . 0.4142135624) (91 . 0) (10 -40.5450002034 53.9053443463) (40 . 0.0000000000) (41 . 0.0000000000) (42 . 0.0000000000) (91 . 0) (10 -40.5450002034 55.4553443463) (40 . 0.0000000000) (41 . 0.0000000000) (42 . -0.4142135624) (91 . 0) (10 -40.3450002034 55.6553443463) (40 . 0.0000000000) (41 . 0.0000000000) (42 . 0.0000000000) (91 . 0) (10 -39.3450002034 55.6553443463) (40 . 0.0000000000) (41 . 0.0000000000) (42 . -0.4142135624) (91 . 0) (10 -39.1450002034 55.4553443463) (40 . 0.0000000000) (41 . 0.0000000000) (42 . 0.0000000000) (91 . 0) (10 -39.1450002034 54.1047561586) (40 . 0.0000000000) (41 . 0.0000000000) (42 . 0.4142135624) (91 . 0) (10 -38.8450002034 53.8047561586) (40 . 0.0000000000) (41 . 0.0000000000) (42 . 0.0000000000) (91 . 0) (10 -36.9570662312 53.8047561586) (40 . 0.0000000000) (41 . 0.0000000000) (42 . 0.0120642717) (91 . 0) (10 -36.9329482207 53.8053381758) (40 . 0.0000000000) (41 . 0.0000000000) (42 . 0.0000000000) (91 . 0) (10 -31.2094830491 54.0817371001) (40 . 0.0000000000) (41 . 0.0000000000) (42 . 0.9528731560) (91 . 0) (10 -31.2094830491 54.7809222760) (40 . 0.0000000000) (41 . 0.0000000000) (42 . 0.0000000000) (91 . 0) (10 -37.4691182139 55.0832140476) (40 . 0.0000000000) (41 . 0.0000000000) (42 . -0.4001496687) (91 . 0) (10 -37.9450002034 55.5826320304) (40 . 0.0000000000) (41 . 0.0000000000) (42 . 0.0000000000) (91 . 0) (10 -37.9450002034 57.0104512351) (40 . 0.0000000000) (41 . 0.0000000000) (42 . -0.4001496687) (91 . 0) (10 -37.4691182139 57.5098692179) (40 . 0.0000000000) (41 . 0.0000000000) (42 . 0.0000000000) (91 . 0) (10 -31.2094830491 57.8121609895) (40 . 0.0000000000) (41 . 0.0000000000) (42 . 0.9528731560) (91 . 0) (10 -31.2094830491 58.5113461655) (40 . 0.0000000000) (41 . 0.0000000000) (42 . 0.0000000000) (91 . 0) (10 -37.4691182139 58.8136379370) (40 . 0.0000000000) (41 . 0.0000000000) (42 . -0.4001496687) (91 . 0) (10 -37.9450002034 59.3130559198) (40 . 0.0000000000) (41 . 0.0000000000) (42 . 0.0000000000) (91 . 0) (10 -37.9450002034 61.2129057277) (40 . 0.0000000000) (41 . 0.0000000000) (42 . -0.4135828614) (91 . 0) (210 0.0000000000 0.0000000000 -1.0000000000))
((0 . "LWPOLYLINE") (100 . "AcDbEntity") (67 . 0) (8 . "A-Window") (62 . 151) (6 . "Continuous") (100 . "AcDbPolyline") (90 . 81) (70 . 1) (43 . 0.0000000000) (38 . 0.0000000000) (39 . 0.0000000000) (10 -43.8450502034 27.7553443463) (40 . 0.0000000000) (41 . 0.0000000000) (42 . 0.0000000000) (91 . 0) (10 -46.9421111606 27.7553443463) (40 . 0.0000000000) (41 . 0.0000000000) (42 . -0.4142135624) (91 . 0) (10 -47.1421111606 27.9553443463) (40 . 0.0000000000) (41 . 0.0000000000) (42 . 0.0000000000) (91 . 0) (10 -47.1421111606 29.1553443463) (40 . 0.0000000000) (41 . 0.0000000000) (42 . 0.4142135624) (91 . 0) (10 -47.3421111606 29.3553443463) (40 . 0.0000000000) (41 . 0.0000000000) (42 . 0.0000000000) (91 . 0) (10 -48.4421111606 29.3553443463) (40 . 0.0000000000) (41 . 0.0000000000) (42 . 0.4142135624) (91 . 0) (10 -48.6421111606 29.1553443463) (40 . 0.0000000000) (41 . 0.0000000000) (42 . 0.0000000000) (91 . 0) (10 -48.6421111606 26.9053443463) (40 . 0.0000000000) (41 . 0.0000000000) (42 . -0.4142135624) (91 . 0) (10 -48.8421111606 26.7053443463) (40 . 0.0000000000) (41 . 0.0000000000) (42 . 0.0000000000) (91 . 0) (10 -54.1421111606 26.7053443463) (40 . 0.0000000000) (41 . 0.0000000000) (42 . -0.4142135624) (91 . 0) (10 -54.4421111606 27.0053443463) (40 . 0.0000000000) (41 . 0.0000000000) (42 . 0.0000000000) (91 . 0) (10 -54.4421111606 27.7053443463) (40 . 0.0000000000) (41 . 0.0000000000) (42 . -0.4142135624) (91 . 0) (10 -54.1421111606 28.0053443463) (40 . 0.0000000000) (41 . 0.0000000000) (42 . 0.0000000000) (91 . 0) (10 -53.2421111606 28.0053443463) (40 . 0.0000000000) (41 . 0.0000000000) (42 . 0.4142135624) (91 . 0) (10 -52.9421111606 28.3053443463) (40 . 0.0000000000) (41 . 0.0000000000) (42 . 0.0000000000) (91 . 0) (10 -52.9421111606 28.9053443463) (40 . 0.0000000000) (41 . 0.0000000000) (42 . 0.4142135624) (91 . 0) (10 -53.2421111606 29.2053443463) (40 . 0.0000000000) (41 . 0.0000000000) (42 . 0.0000000000) (91 . 0) (10 -55.6421111606 29.2053443463) (40 . 0.0000000000) (41 . 0.0000000000) (42 . 0.4142135624) (91 . 0) (10 -55.9421111606 28.9053443463) (40 . 0.0000000000) (41 . 0.0000000000) (42 . 0.0000000000) (91 . 0) (10 -55.9421111606 27.0053443463) (40 . 0.0000000000) (41 . 0.0000000000) (42 . -0.4142135624) (91 . 0) (10 -56.2421111606 26.7053443463) (40 . 0.0000000000) (41 . 0.0000000000) (42 . 0.0000000000) (91 . 0) (10 -59.1421111606 26.7053443463) (40 . 0.0000000000) (41 . 0.0000000000) (42 . -0.4142135624) (91 . 0) (10 -59.4421111606 27.0053443463) (40 . 0.0000000000) (41 . 0.0000000000) (42 . 0.0000000000) (91 . 0) (10 -59.4421111606 29.0553443463) (40 . 0.0000000000) (41 . 0.0000000000) (42 . 0.4142135624) (91 . 0) (10 -59.7421111606 29.3553443463) (40 . 0.0000000000) (41 . 0.0000000000) (42 . 0.0000000000) (91 . 0) (10 -60.3421111606 29.3553443463) (40 . 0.0000000000) (41 . 0.0000000000) (42 . 0.4142135624) (91 . 0) (10 -60.6421111606 29.0553443463) (40 . 0.0000000000) (41 . 0.0000000000) (42 . 0.0000000000) (91 . 0) (10 -60.6421111606 25.5053443463) (40 . 0.0000000000) (41 . 0.0000000000) (42 . 0.4142135624) (91 . 0) (10 -60.3421111606 25.2053443463) (40 . 0.0000000000) (41 . 0.0000000000) (42 . 0.0000000000) (91 . 0) (10 -48.8421111606 25.2053443463) (40 . 0.0000000000) (41 . 0.0000000000) (42 . -0.4142135624) (91 . 0) (10 -48.6421111606 25.0053443463) (40 . 0.0000000000) (41 . 0.0000000000) (42 . 0.0000000000) (91 . 0) (10 -48.6421111606 24.3553443463) (40 . 0.0000000000) (41 . 0.0000000000) (42 . 0.4142135624) (91 . 0) (10 -48.1421111606 23.8553443463) (40 . 0.0000000000) (41 . 0.0000000000) (42 . 0.0000000000) (91 . 0) (10 -46.2421111606 23.8553443463) (40 . 0.0000000000) (41 . 0.0000000000) (42 . 0.4142135624) (91 . 0) (10 -45.9421111606 24.1553443463) (40 . 0.0000000000) (41 . 0.0000000000) (42 . 0.0000000000) (91 . 0) (10 -45.9421111606 24.5553443463) (40 . 0.0000000000) (41 . 0.0000000000) (42 . 0.4142135624) (91 . 0) (10 -46.2421111606 24.8553443463) (40 . 0.0000000000) (41 . 0.0000000000) (42 . 0.0000000000) (91 . 0) (10 -47.1421111606 24.8553443463) (40 . 0.0000000000) (41 . 0.0000000000) (42 . -0.4142135624) (91 . 0) (10 -47.4421111606 25.1553443463) (40 . 0.0000000000) (41 . 0.0000000000) (42 . 0.0000000000) (91 . 0) (10 -47.4421111606 25.7553443463) (40 . 0.0000000000) (41 . 0.0000000000) (42 . -0.4142135624) (91 . 0) (10 -46.9421111606 26.2553443463) (40 . 0.0000000000) (41 . 0.0000000000) (42 . 0.0000000000) (91 . 0) (10 -44.1421111606 26.2553443463) (40 . 0.0000000000) (41 . 0.0000000000) (42 . 0.0000000000) (91 . 0) (10 -41.3421111606 26.2553443463) (40 . 0.0000000000) (41 . 0.0000000000) (42 . -0.4142135624) (91 . 0) (10 -40.8421111606 25.7553443463) (40 . 0.0000000000) (41 . 0.0000000000) (42 . 0.0000000000) (91 . 0) (10 -40.8421111606 25.1553443463) (40 . 0.0000000000) (41 . 0.0000000000) (42 . -0.4142135624) (91 . 0) (10 -41.1421111606 24.8553443463) (40 . 0.0000000000) (41 . 0.0000000000) (42 . 0.0000000000) (91 . 0) (10 -42.0421111606 24.8553443463) (40 . 0.0000000000) (41 . 0.0000000000) (42 . 0.4142135624) (91 . 0) (10 -42.3421111606 24.5553443463) (40 . 0.0000000000) (41 . 0.0000000000) (42 . 0.0000000000) (91 . 0) (10 -42.3421111606 24.1553443463) (40 . 0.0000000000) (41 . 0.0000000000) (42 . 0.4142135624) (91 . 0) (10 -42.0421111606 23.8553443463) (40 . 0.0000000000) (41 . 0.0000000000) (42 . 0.0000000000) (91 . 0) (10 -40.1421111606 23.8553443463) (40 . 0.0000000000) (41 . 0.0000000000) (42 . 0.4142135624) (91 . 0) (10 -39.6421111606 24.3553443463) (40 . 0.0000000000) (41 . 0.0000000000) (42 . 0.0000000000) (91 . 0) (10 -39.6421111606 27.2553443463) (40 . 0.0000000000) (41 . 0.0000000000) (42 . 0.4142135624) (91 . 0) (10 -40.1421111606 27.7553443463) (40 . 0.0000000000) (41 . 0.0000000000) (42 . 0.0000000000) (91 . 0) (10 -41.1450502034 27.7553443463) (40 . 0.0000000000) (41 . 0.0000000000) (42 . -0.4142135624) (91 . 0) (10 -41.6450502034 28.2553443463) (40 . 0.0000000000) (41 . 0.0000000000) (42 . 0.0000000000) (91 . 0) (10 -41.6450502034 51.1553443463) (40 . 0.0000000000) (41 . 0.0000000000) (42 . -0.4142135624) (91 . 0) (10 -41.1450502034 51.6553443463) (40 . 0.0000000000) (41 . 0.0000000000) (42 . 0.0000000000) (91 . 0) (10 -39.7450502034 51.6553443463) (40 . 0.0000000000) (41 . 0.0000000000) (42 . 0.4142135624) (91 . 0) (10 -39.2450502034 52.1553443463) (40 . 0.0000000000) (41 . 0.0000000000) (42 . 0.0000000000) (91 . 0) (10 -39.2450502034 54.9553443465) (40 . 0.0000000000) (41 . 0.0000000000) (42 . 0.4142135624) (91 . 0) (10 -39.4450502034 55.1553443465) (40 . 0.0000000000) (41 . 0.0000000000) (42 . 0.0000000000) (91 . 0) (10 -40.0450502034 55.1553443465) (40 . 0.0000000000) (41 . 0.0000000000) (42 . 0.4142135624) (91 . 0) (10 -40.2450502034 54.9553443465) (40 . 0.0000000000) (41 . 0.0000000000) (42 . 0.0000000000) (91 . 0) (10 -40.2450502034 53.6552443463) (40 . 0.0000000000) (41 . 0.0000000000) (42 . -0.4142135624) (91 . 0) (10 -40.7449502034 53.1553443463) (40 . 0.0000000000) (41 . 0.0000000000) (42 . 0.0000000000) (91 . 0) (10 -41.7450502034 53.1553443463) (40 . 0.0000000000) (41 . 0.0000000000) (42 . -0.4142135624) (91 . 0) (10 -42.1450502034 53.5553443463) (40 . 0.0000000000) (41 . 0.0000000000) (42 . 0.0000000000) (91 . 0) (10 -42.1450502034 60.2553443463) (40 . 0.0000000000) (41 . 0.0000000000) (42 . -0.4142135624) (91 . 0) (10 -41.7450502034 60.6553443463) (40 . 0.0000000000) (41 . 0.0000000000) (42 . 0.0000000000) (91 . 0) (10 -40.7449502034 60.6553443463) (40 . 0.0000000000) (41 . 0.0000000000) (42 . -0.4142135624) (91 . 0) (10 -40.2450502034 60.1554443463) (40 . 0.0000000000) (41 . 0.0000000000) (42 . 0.0000000000) (91 . 0) (10 -40.2450502034 58.8553443462) (40 . 0.0000000000) (41 . 0.0000000000) (42 . 0.4142135624) (91 . 0) (10 -40.0450502034 58.6553443462) (40 . 0.0000000000) (41 . 0.0000000000) (42 . 0.0000000000) (91 . 0) (10 -39.4450502034 58.6553443462) (40 . 0.0000000000) (41 . 0.0000000000) (42 . 0.4142135624) (91 . 0) (10 -39.2450502034 58.8553443462) (40 . 0.0000000000) (41 . 0.0000000000) (42 . 0.0000000000) (91 . 0) (10 -39.2450502034 61.4553443463) (40 . 0.0000000000) (41 . 0.0000000000) (42 . 0.4142135624) (91 . 0) (10 -39.6450502034 61.8553443463) (40 . 0.0000000000) (41 . 0.0000000000) (42 . 0.0000000000) (91 . 0) (10 -43.2450502034 61.8553443463) (40 . 0.0000000000) (41 . 0.0000000000) (42 . 0.4142135624) (91 . 0) (10 -43.6450502034 61.4553443463) (40 . 0.0000000000) (41 . 0.0000000000) (42 . 0.0000000000) (91 . 0) (10 -43.6450502034 27.9553443463) (40 . 0.0000000000) (41 . 0.0000000000) (42 . -0.4142135624) (91 . 0) (210 0.0000000000 0.0000000000 -1.0000000000))
((0 . "LWPOLYLINE") (100 . "AcDbEntity") (67 . 0) (8 . "A-Window") (62 . 151) (6 . "Continuous") (100 . "AcDbPolyline") (90 . 2) (70 . 0) (43 . 0.0000000000) (38 . 0.0000000000) (39 . 0.0000000000) (10 -46.6421111606 38.8497574418) (40 . 0.0000000000) (41 . 0.0000000000) (42 . 0.0000000000) (91 . 0) (10 -46.6421111606 30.3553443463) (40 . 0.0000000000) (41 . 0.0000000000) (42 . 0.0000000000) (91 . 0) (210 0.0000000000 0.0000000000 -1.0000000000))
((0 . "LWPOLYLINE") (100 . "AcDbEntity") (67 . 0) (8 . "A-Window") (62 . 151) (6 . "Continuous") (100 . "AcDbPolyline") (90 . 2) (70 . 0) (43 . 0.0000000000) (38 . 0.0000000000) (39 . 0.0000000000) (10 -60.6421111606 30.8553443463) (40 . 0.0000000000) (41 . 0.0000000000) (42 . 0.0000000000) (91 . 0) (10 -60.6421111606 38.8553443463) (40 . 0.0000000000) (41 . 0.0000000000) (42 . 0.0000000000) (91 . 0) (210 0.0000000000 0.0000000000 -1.0000000000))
((0 . "ARC") (100 . "AcDbEntity") (67 . 0) (8 . "A-Window") (62 . 151) (6 . "Continuous") (100 . "AcDbCircle") (10 -47.0846151836 78.3974005150 0.0000000000) (40 . 15.5520516883) (210 0.0000000000 0.0000000000 -1.0000000000) (100 . "AcDbArc") (50 . -1.6066511102) (51 . -1.3878946035))
((0 . "LINE") (100 . "AcDbEntity") (67 . 0) (8 . "A-Window") (62 . 151) (6 . "Continuous") (100 . "AcDbLine") (10 46.6421111606 43.0415554178 0.0000000000) (11 43.6450502034 43.0415554178 0.0000000000) (210 0.0000000000 0.0000000000 1.0000000000))
((0 . "LINE") (100 . "AcDbEntity") (67 . 0) (8 . "A-Window") (62 . 151) (6 . "Continuous") (100 . "AcDbLine") (10 44.2559511346 58.9047561586 0.0000000000) (11 43.6450502034 58.9047561586 0.0000000000) (210 0.0000000000 0.0000000000 1.0000000000))
((0 . "LWPOLYLINE") (100 . "AcDbEntity") (67 . 0) (8 . "A-Window") (62 . 151) (6 . "Continuous") (100 . "AcDbPolyline") (90 . 27) (70 . 1) (43 . 0.0000000000) (38 . 0.0000000000) (39 . 0.0000000000) (10 -952.6498781166 26.2511348351) (40 . 0.0000000000) (41 . 0.0000000000) (42 . 0.0000000000) (91 . 0) (10 -957.6339442029 26.2576674747) (40 . 0.0000000000) (41 . 0.0000000000) (42 . 0.0000000000) (91 . 0) (10 -957.6339442029 25.4345600775) (40 . 0.0000000000) (41 . 0.0000000000) (42 . 0.4142135624) (91 . 0) (10 -957.4339442029 25.2345600775) (40 . 0.0000000000) (41 . 0.0000000000) (42 . 0.0000000000) (91 . 0) (10 -956.3549967714 25.2345600775) (40 . 0.0000000000) (41 . 0.0000000000) (42 . -0.4142135624) (91 . 0) (10 -956.1549967713 25.0345600775) (40 . 0.0000000000) (41 . 0.0000000000) (42 . 0.0000000000) (91 . 0) (10 -956.1549967713 24.3317958718) (40 . 0.0000000000) (41 . 0.0000000000) (42 . -0.4142135624) (91 . 0) (10 -956.6549967713 23.8317958718) (40 . 0.0000000000) (41 . 0.0000000000) (42 . 0.0000000000) (91 . 0) (10 -957.7446429326 23.8317958718) (40 . 0.0000000000) (41 . 0.0000000000) (42 . 0.4142135624) (91 . 0) (10 -958.2446429326 23.3317958718) (40 . 0.0000000000) (41 . 0.0000000000) (42 . 0.0000000000) (91 . 0) (10 -958.2446429326 22.4328904394) (40 . 0.0000000000) (41 . 0.0000000000) (42 . 0.1452621195) (91 . 0) (10 -958.0283749772 21.7041923176) (40 . 0.0000000000) (41 . 0.0000000000) (42 . 0.1071711367) (91 . 0) (10 -957.3030199715 20.9862582434) (40 . 0.0000000000) (41 . 0.0000000000) (42 . 0.0774042911) (91 . 0) (10 -956.3129749158 20.5533278264) (40 . 0.0000000000) (41 . 0.0000000000) (42 . 0.0645213706) (91 . 0) (10 -955.0297410482 20.3870435680) (40 . 0.0000000000) (41 . 0.0000000000) (42 . 0.0645213706) (91 . 0) (10 -953.7465071807 20.5533278264) (40 . 0.0000000000) (41 . 0.0000000000) (42 . 0.0774042911) (91 . 0) (10 -952.7564621249 20.9862582434) (40 . 0.0000000000) (41 . 0.0000000000) (42 . 0.1071711367) (91 . 0) (10 -952.0311071193 21.7041923176) (40 . 0.0000000000) (41 . 0.0000000000) (42 . 0.1452621195) (91 . 0) (10 -951.8148391639 22.4328904394) (40 . 0.0000000000) (41 . 0.0000000000) (42 . 0.0000000000) (91 . 0) (10 -951.8148391639 23.3317958718) (40 . 0.0000000000) (41 . 0.0000000000) (42 . 0.4142135624) (91 . 0) (10 -952.3148391639 23.8317958718) (40 . 0.0000000000) (41 . 0.0000000000) (42 . 0.0000000000) (91 . 0) (10 -953.6549967714 23.8317958718) (40 . 0.0000000000) (41 . 0.0000000000) (42 . -0.4142135624) (91 . 0) (10 -954.1549967714 24.3317958718) (40 . 0.0000000000) (41 . 0.0000000000) (42 . 0.0000000000) (91 . 0) (10 -954.1549967714 25.0345600775) (40 . 0.0000000000) (41 . 0.0000000000) (42 . -0.4142135624) (91 . 0) (10 -953.9549967714 25.2345600775) (40 . 0.0000000000) (41 . 0.0000000000) (42 . 0.0000000000) (91 . 0) (10 -952.8498781166 25.2345600775) (40 . 0.0000000000) (41 . 0.0000000000) (42 . 0.4142135624) (91 . 0) (10 -952.6498781166 25.4345600775) (40 . 0.0000000000) (41 . 0.0000000000) (42 . 0.0000000000) (91 . 0) (210 0.0000000000 0.0000000000 -1.0000000000))
((0 . "LWPOLYLINE") (100 . "AcDbEntity") (67 . 0) (8 . "A-Window") (62 . 151) (6 . "Continuous") (370 . -3) (100 . "AcDbPolyline") (90 . 21) (70 . 1) (43 . 0.0000000000) (38 . 0.0000000000) (39 . 0.0000000000) (10 -952.3148391638 22.4328904394) (40 . 0.0000000000) (41 . 0.0000000000) (42 . -0.1452621195) (91 . 0) (10 -952.4501551775 21.9769536142) (40 . 0.0000000000) (41 . 0.0000000000) (42 . -0.1071711367) (91 . 0) (10 -953.0248998913 21.4080889742) (40 . 0.0000000000) (41 . 0.0000000000) (42 . -0.0774042911) (91 . 0) (10 -953.8739494214 21.0368135813) (40 . 0.0000000000) (41 . 0.0000000000) (42 . -0.0645213706) (91 . 0) (10 -955.0297410482 20.8870435679) (40 . 0.0000000000) (41 . 0.0000000000) (42 . -0.0645213706) (91 . 0) (10 -956.1855326751 21.0368135813) (40 . 0.0000000000) (41 . 0.0000000000) (42 . -0.0774042911) (91 . 0) (10 -957.0345822051 21.4080889742) (40 . 0.0000000000) (41 . 0.0000000000) (42 . -0.1071711367) (91 . 0) (10 -957.6093269190 21.9769536142) (40 . 0.0000000000) (41 . 0.0000000000) (42 . -0.1452621195) (91 . 0) (10 -957.7446429326 22.4328904394) (40 . 0.0000000000) (41 . 0.0000000000) (42 . 0.0000000000) (91 . 0) (10 -957.7446429326 22.8345600778) (40 . 0.0000000000) (41 . 0.0000000000) (42 . -0.4142135624) (91 . 0) (10 -957.2446429326 23.3345600778) (40 . 0.0000000000) (41 . 0.0000000000) (42 . 0.0000000000) (91 . 0) (10 -955.9962871612 23.3345600778) (40 . 0.0000000000) (41 . 0.0000000000) (42 . 0.3939487093) (91 . 0) (10 -955.4975005229 23.7997478750) (40 . 0.0000000000) (41 . 0.0000000000) (42 . 0.0000000000) (91 . 0) (10 -955.4103464472 25.0484849586) (40 . 0.0000000000) (41 . 0.0000000000) (42 . -0.3939487093) (91 . 0) (10 -955.2108317918 25.2345600775) (40 . 0.0000000000) (41 . 0.0000000000) (42 . 0.0000000000) (91 . 0) (10 -955.0821705733 25.2345600775) (40 . 0.0000000000) (41 . 0.0000000000) (42 . -0.3852515762) (91 . 0) (10 -954.8831674381 25.0545038024) (40 . 0.0000000000) (41 . 0.0000000000) (42 . 0.0000000000) (91 . 0) (10 -954.7559101347 23.7847007656) (40 . 0.0000000000) (41 . 0.0000000000) (42 . 0.3852515762) (91 . 0) (10 -954.2584022966 23.3345600777) (40 . 0.0000000000) (41 . 0.0000000000) (42 . 0.0000000000) (91 . 0) (10 -952.8148391638 23.3345600778) (40 . 0.0000000000) (41 . 0.0000000000) (42 . -0.4142135624) (91 . 0) (10 -952.3148391638 22.8345600778) (40 . 0.0000000000) (41 . 0.0000000000) (42 . 0.0000000000) (91 . 0) (210 0.0000000000 0.0000000000 -1.0000000000))
((0 . "LWPOLYLINE") (100 . "AcDbEntity") (67 . 0) (8 . "A-Window") (62 . 151) (6 . "Continuous") (100 . "AcDbPolyline") (90 . 27) (70 . 1) (43 . 0.0000000000) (38 . 0.0000000000) (39 . 0.0000000000) (10 -957.6339442015 26.2512293331) (40 . 0.0000000000) (41 . 0.0000000000) (42 . 0.0000000000) (91 . 0) (10 -952.6498781180 26.2577619726) (40 . 0.0000000000) (41 . 0.0000000000) (42 . 0.0000000000) (91 . 0) (10 -952.6498781180 25.4346545759) (40 . 0.0000000000) (41 . 0.0000000000) (42 . -0.4142135624) (91 . 0) (10 -952.8498781179 25.2346545760) (40 . 0.0000000000) (41 . 0.0000000000) (42 . 0.0000000000) (91 . 0) (10 -953.9288255489 25.2346545760) (40 . 0.0000000000) (41 . 0.0000000000) (42 . 0.4142135624) (91 . 0) (10 -954.1288255487 25.0346545762) (40 . 0.0000000000) (41 . 0.0000000000) (42 . 0.0000000000) (91 . 0) (10 -954.1288255487 24.3318903708) (40 . 0.0000000000) (41 . 0.0000000000) (42 . 0.4142135624) (91 . 0) (10 -953.6288255490 23.8318903711) (40 . 0.0000000000) (41 . 0.0000000000) (42 . 0.0000000000) (91 . 0) (10 -952.5391793884 23.8318903711) (40 . 0.0000000000) (41 . 0.0000000000) (42 . -0.4142135624) (91 . 0) (10 -952.0391793887 23.3318903714) (40 . 0.0000000000) (41 . 0.0000000000) (42 . 0.0000000000) (91 . 0) (10 -952.0391793887 22.4329849395) (40 . 0.0000000000) (41 . 0.0000000000) (42 . -0.1452621195) (91 . 0) (10 -952.2554473440 21.7042868181) (40 . 0.0000000000) (41 . 0.0000000000) (42 . -0.1071711367) (91 . 0) (10 -952.9808023492 20.9863527442) (40 . 0.0000000000) (41 . 0.0000000000) (42 . -0.0774042911) (91 . 0) (10 -953.9708474044 20.5534223275) (40 . 0.0000000000) (41 . 0.0000000000) (42 . -0.0645213706) (91 . 0) (10 -955.2540812712 20.3871380692) (40 . 0.0000000000) (41 . 0.0000000000) (42 . -0.0645213706) (91 . 0) (10 -956.5373151380 20.5534223275) (40 . 0.0000000000) (41 . 0.0000000000) (42 . -0.0774042911) (91 . 0) (10 -957.5273601933 20.9863527442) (40 . 0.0000000000) (41 . 0.0000000000) (42 . -0.1071711367) (91 . 0) (10 -958.2527151985 21.7042868181) (40 . 0.0000000000) (41 . 0.0000000000) (42 . -0.1452621195) (91 . 0) (10 -958.4689831538 22.4329849395) (40 . 0.0000000000) (41 . 0.0000000000) (42 . 0.0000000000) (91 . 0) (10 -958.4689831538 23.3318903714) (40 . 0.0000000000) (41 . 0.0000000000) (42 . -0.4142135624) (91 . 0) (10 -957.9689831541 23.8318903711) (40 . 0.0000000000) (41 . 0.0000000000) (42 . 0.0000000000) (91 . 0) (10 -956.6288255473 23.8318903711) (40 . 0.0000000000) (41 . 0.0000000000) (42 . 0.4142135624) (91 . 0) (10 -956.1288255476 24.3318903708) (40 . 0.0000000000) (41 . 0.0000000000) (42 . 0.0000000000) (91 . 0) (10 -956.1288255476 25.0346545761) (40 . 0.0000000000) (41 . 0.0000000000) (42 . 0.4142135624) (91 . 0) (10 -956.3288255475 25.2346545760) (40 . 0.0000000000) (41 . 0.0000000000) (42 . 0.0000000000) (91 . 0) (10 -957.4339442016 25.2346545760) (40 . 0.0000000000) (41 . 0.0000000000) (42 . -0.4142135624) (91 . 0) (10 -957.6339442015 25.4346545759) (40 . 0.0000000000) (41 . 0.0000000000) (42 . 0.0000000000) (91 . 0) (210 0.0000000000 0.0000000000 -1.0000000000))
((0 . "LWPOLYLINE") (100 . "AcDbEntity") (67 . 0) (8 . "A-Window") (62 . 151) (6 . "Continuous") (370 . -3) (100 . "AcDbPolyline") (90 . 21) (70 . 1) (43 . 0.0000000000) (38 . 0.0000000000) (39 . 0.0000000000) (10 -957.9689831541 22.4329849395) (40 . 0.0000000000) (41 . 0.0000000000) (42 . 0.1452621195) (91 . 0) (10 -957.8336671405 21.9770481145) (40 . 0.0000000000) (41 . 0.0000000000) (42 . 0.1071711367) (91 . 0) (10 -957.2589224270 21.4081834749) (40 . 0.0000000000) (41 . 0.0000000000) (42 . 0.0774042911) (91 . 0) (10 -956.4098728974 21.0369080822) (40 . 0.0000000000) (41 . 0.0000000000) (42 . 0.0645213706) (91 . 0) (10 -955.2540812712 20.8871380688) (40 . 0.0000000000) (41 . 0.0000000000) (42 . 0.0645213706) (91 . 0) (10 -954.0982896450 21.0369080822) (40 . 0.0000000000) (41 . 0.0000000000) (42 . 0.0774042911) (91 . 0) (10 -953.2492401155 21.4081834749) (40 . 0.0000000000) (41 . 0.0000000000) (42 . 0.1071711367) (91 . 0) (10 -952.6744954019 21.9770481145) (40 . 0.0000000000) (41 . 0.0000000000) (42 . 0.1452621195) (91 . 0) (10 -952.5391793884 22.4329849395) (40 . 0.0000000000) (41 . 0.0000000000) (42 . 0.0000000000) (91 . 0) (10 -952.5391793884 22.8346545776) (40 . 0.0000000000) (41 . 0.0000000000) (42 . 0.4142135624) (91 . 0) (10 -953.0391793881 23.3346545773) (40 . 0.0000000000) (41 . 0.0000000000) (42 . 0.0000000000) (91 . 0) (10 -954.2875351587 23.3346545773) (40 . 0.0000000000) (41 . 0.0000000000) (42 . -0.3939487093) (91 . 0) (10 -954.7863217968 23.7998423743) (40 . 0.0000000000) (41 . 0.0000000000) (42 . 0.0000000000) (91 . 0) (10 -954.8734758725 25.0485794572) (40 . 0.0000000000) (41 . 0.0000000000) (42 . 0.3939487093) (91 . 0) (10 -955.0729905277 25.2346545760) (40 . 0.0000000000) (41 . 0.0000000000) (42 . 0.0000000000) (91 . 0) (10 -955.2016517461 25.2346545760) (40 . 0.0000000000) (41 . 0.0000000000) (42 . 0.3852515762) (91 . 0) (10 -955.4006548813 25.0545983010) (40 . 0.0000000000) (41 . 0.0000000000) (42 . 0.0000000000) (91 . 0) (10 -955.5279121846 23.7847952650) (40 . 0.0000000000) (41 . 0.0000000000) (42 . -0.3852515762) (91 . 0) (10 -956.0254200224 23.3346545773) (40 . 0.0000000000) (41 . 0.0000000000) (42 . 0.0000000000) (91 . 0) (10 -957.4689831544 23.3346545773) (40 . 0.0000000000) (41 . 0.0000000000) (42 . 0.4142135624) (91 . 0) (10 -957.9689831541 22.8346545776) (40 . 0.0000000000) (41 . 0.0000000000) (42 . 0.0000000000) (91 . 0) (210 0.0000000000 0.0000000000 -1.0000000000))
((0 . "LWPOLYLINE") (100 . "AcDbEntity") (67 . 0) (8 . "A-Window") (62 . 151) (6 . "Continuous") (100 . "AcDbPolyline") (90 . 28) (70 . 1) (43 . 0.0000000000) (38 . 0.0000000000) (39 . 0.0000000000) (10 -923.1421111598 23.0553443461) (40 . 0.0000000000) (41 . 0.0000000000) (42 . 0.0000000000) (91 . 0) (10 -923.1421111598 -20.3446556539) (40 . 0.0000000000) (41 . 0.0000000000) (42 . -0.4142135624) (91 . 0) (10 -923.4421111598 -20.6446556539) (40 . 0.0000000000) (41 . 0.0000000000) (42 . 0.0000000000) (91 . 0) (10 -929.6421111598 -20.6446556539) (40 . 0.0000000000) (41 . 0.0000000000) (42 . -0.4142135624) (91 . 0) (10 -929.9421111598 -20.3446556539) (40 . 0.0000000000) (41 . 0.0000000000) (42 . 0.0000000000) (91 . 0) (10 -929.9421111598 3.1553443461) (40 . 0.0000000000) (41 . 0.0000000000) (42 . 0.4142135624) (91 . 0) (10 -930.9421111598 4.1553443461) (40 . 0.0000000000) (41 . 0.0000000000) (42 . 0.0000000000) (91 . 0) (10 -932.6421111598 4.1553443461) (40 . 0.0000000000) (41 . 0.0000000000) (42 . -0.4142135624) (91 . 0) (10 -933.1421111598 4.6553443461) (40 . 0.0000000000) (41 . 0.0000000000) (42 . 0.0000000000) (91 . 0) (10 -933.1421111598 7.3553443461) (40 . 0.0000000000) (41 . 0.0000000000) (42 . -0.4142135624) (91 . 0) (10 -932.6421111598 7.8553443461) (40 . 0.0000000000) (41 . 0.0000000000) (42 . 0.0000000000) (91 . 0) (10 -930.9421111598 7.8553443461) (40 . 0.0000000000) (41 . 0.0000000000) (42 . 0.4142135624) (91 . 0) (10 -929.9421111598 8.8553443461) (40 . 0.0000000000) (41 . 0.0000000000) (42 . 0.0000000000) (91 . 0) (10 -929.9421111598 18.8553443461) (40 . 0.0000000000) (41 . 0.0000000000) (42 . 0.4142135624) (91 . 0) (10 -930.9421111598 19.8553443461) (40 . 0.0000000000) (41 . 0.0000000000) (42 . 0.0000000000) (91 . 0) (10 -933.6421111598 19.8553443461) (40 . 0.0000000000) (41 . 0.0000000000) (42 . -0.4142135624) (91 . 0) (10 -934.1421111598 20.3553443461) (40 . 0.0000000000) (41 . 0.0000000000) (42 . 0.0000000000) (91 . 0) (10 -934.1421111598 28.8553443461) (40 . 0.0000000000) (41 . 0.0000000000) (42 . -0.4142135624) (91 . 0) (10 -933.6421111598 29.3553443461) (40 . 0.0000000000) (41 . 0.0000000000) (42 . 0.0000000000) (91 . 0) (10 -923.6421111598 29.3553443461) (40 . 0.0000000000) (41 . 0.0000000000) (42 . -0.4142135624) (91 . 0) (10 -923.1421111598 28.8553443461) (40 . 0.0000000000) (41 . 0.0000000000) (42 . 0.0000000000) (91 . 0) (10 -923.1421111598 25.3553443461) (40 . 0.0000000000) (41 . 0.0000000000) (42 . -0.4142135624) (91 . 0) (10 -923.6421111598 24.8553443461) (40 . 0.0000000000) (41 . 0.0000000000) (42 . 0.0000000000) (91 . 0) (10 -924.1421111598 24.8553443461) (40 . 0.0000000000) (41 . 0.0000000000) (42 . 0.4142135624) (91 . 0) (10 -924.6421111598 24.3553443461) (40 . 0.0000000000) (41 . 0.0000000000) (42 . 0.0000000000) (91 . 0) (10 -924.6421111598 23.8553443461) (40 . 0.0000000000) (41 . 0.0000000000) (42 . 0.4142135624) (91 . 0) (10 -924.1421111598 23.3553443461) (40 . 0.0000000000) (41 . 0.0000000000) (42 . 0.0000000000) (91 . 0) (10 -923.4421111598 23.3553443461) (40 . 0.0000000000) (41 . 0.0000000000) (42 . -0.4142135624) (91 . 0) (210 0.0000000000 0.0000000000 -1.0000000000))
((0 . "LWPOLYLINE") (100 . "AcDbEntity") (67 . 0) (8 . "A-Window") (62 . 151) (6 . "Continuous") (100 . "AcDbPolyline") (90 . 71) (70 . 1) (43 . 0.0000000000) (38 . 0.0000000000) (39 . 0.0000000000) (10 -947.8421111598 29.0553443461) (40 . 0.0000000000) (41 . 0.0000000000) (42 . 0.0000000000) (91 . 0) (10 -947.8421111598 27.3553443461) (40 . 0.0000000000) (41 . 0.0000000000) (42 . 0.4142135624) (91 . 0) (10 -947.3421111598 26.8553443461) (40 . 0.0000000000) (41 . 0.0000000000) (42 . 0.0000000000) (91 . 0) (10 -945.1421111598 26.8553443461) (40 . 0.0000000000) (41 . 0.0000000000) (42 . 0.4142135624) (91 . 0) (10 -944.8421111598 27.1553443461) (40 . 0.0000000000) (41 . 0.0000000000) (42 . 0.0000000000) (91 . 0) (10 -944.8421111598 27.5553443461) (40 . 0.0000000000) (41 . 0.0000000000) (42 . 0.4142135624) (91 . 0) (10 -945.1421111598 27.8553443461) (40 . 0.0000000000) (41 . 0.0000000000) (42 . 0.0000000000) (91 . 0) (10 -946.0421111598 27.8553443461) (40 . 0.0000000000) (41 . 0.0000000000) (42 . -0.4142135624) (91 . 0) (10 -946.3421111598 28.1553443461) (40 . 0.0000000000) (41 . 0.0000000000) (42 . 0.0000000000) (91 . 0) (10 -946.3421111598 29.0553443461) (40 . 0.0000000000) (41 . 0.0000000000) (42 . -0.4142135624) (91 . 0) (10 -946.0421111598 29.3553443461) (40 . 0.0000000000) (41 . 0.0000000000) (42 . 0.0000000000) (91 . 0) (10 -936.1421111598 29.3553443461) (40 . 0.0000000000) (41 . 0.0000000000) (42 . -0.4142135624) (91 . 0) (10 -935.6421111598 28.8553443461) (40 . 0.0000000000) (41 . 0.0000000000) (42 . 0.0000000000) (91 . 0) (10 -935.6421111598 18.8553443461) (40 . 0.0000000000) (41 . 0.0000000000) (42 . 0.4142135624) (91 . 0) (10 -935.1421111598 18.3553443461) (40 . 0.0000000000) (41 . 0.0000000000) (42 . 0.0000000000) (91 . 0) (10 -931.9421111598 18.3553443461) (40 . 0.0000000000) (41 . 0.0000000000) (42 . -0.4142135624) (91 . 0) (10 -931.4421111598 17.8553443461) (40 . 0.0000000000) (41 . 0.0000000000) (42 . 0.0000000000) (91 . 0) (10 -931.4421111598 9.8553443461) (40 . 0.0000000000) (41 . 0.0000000000) (42 . -0.4142135624) (91 . 0) (10 -931.9421111598 9.3553443461) (40 . 0.0000000000) (41 . 0.0000000000) (42 . 0.0000000000) (91 . 0) (10 -933.9421111598 9.3553443461) (40 . 0.0000000000) (41 . 0.0000000000) (42 . -0.4142135624) (91 . 0) (10 -934.4421111598 9.8553443461) (40 . 0.0000000000) (41 . 0.0000000000) (42 . 0.0000000000) (91 . 0) (10 -934.4421111598 11.6553443461) (40 . 0.0000000000) (41 . 0.0000000000) (42 . 0.4142135624) (91 . 0) (10 -934.9421111598 12.1553443461) (40 . 0.0000000000) (41 . 0.0000000000) (42 . 0.0000000000) (91 . 0) (10 -935.1421111598 12.1553443461) (40 . 0.0000000000) (41 . 0.0000000000) (42 . 0.4142135624) (91 . 0) (10 -935.6421111598 11.6553443461) (40 . 0.0000000000) (41 . 0.0000000000) (42 . 0.0000000000) (91 . 0) (10 -935.6421111598 6.6867151960) (40 . 0.0000000000) (41 . 0.0000000000) (42 . 0.1989123674) (91 . 0) (10 -935.4956645504 6.3331618054) (40 . 0.0000000000) (41 . 0.0000000000) (42 . 0.0000000000) (91 . 0) (10 -935.2299791254 6.0674763805) (40 . 0.0000000000) (41 . 0.0000000000) (42 . -0.4142135624) (91 . 0) (10 -935.2299791254 5.6432123118) (40 . 0.0000000000) (41 . 0.0000000000) (42 . 0.0000000000) (91 . 0) (10 -935.4956645504 5.3775268868) (40 . 0.0000000000) (41 . 0.0000000000) (42 . 0.1989123674) (91 . 0) (10 -935.6421111598 5.0239734962) (40 . 0.0000000000) (41 . 0.0000000000) (42 . 0.0000000000) (91 . 0) (10 -935.6421111598 0.3553443461) (40 . 0.0000000000) (41 . 0.0000000000) (42 . 0.4142135624) (91 . 0) (10 -935.1421111598 -0.1446556539) (40 . 0.0000000000) (41 . 0.0000000000) (42 . 0.0000000000) (91 . 0) (10 -934.9421111598 -0.1446556539) (40 . 0.0000000000) (41 . 0.0000000000) (42 . 0.4142135624) (91 . 0) (10 -934.4421111598 0.3553443461) (40 . 0.0000000000) (41 . 0.0000000000) (42 . 0.0000000000) (91 . 0) (10 -934.4421111598 2.1553443461) (40 . 0.0000000000) (41 . 0.0000000000) (42 . -0.4142135624) (91 . 0) (10 -933.9421111598 2.6553443461) (40 . 0.0000000000) (41 . 0.0000000000) (42 . 0.0000000000) (91 . 0) (10 -931.9421111598 2.6553443461) (40 . 0.0000000000) (41 . 0.0000000000) (42 . -0.4142135624) (91 . 0) (10 -931.4421111598 2.1553443461) (40 . 0.0000000000) (41 . 0.0000000000) (42 . 0.0000000000) (91 . 0) (10 -931.4421111598 -6.8132848040) (40 . 0.0000000000) (41 . 0.0000000000) (42 . 0.1989123674) (91 . 0) (10 -931.2956645504 -7.1668381946) (40 . 0.0000000000) (41 . 0.0000000000) (42 . 0.0000000000) (91 . 0) (10 -931.0299791254 -7.4325236195) (40 . 0.0000000000) (41 . 0.0000000000) (42 . -0.4142135624) (91 . 0) (10 -931.0299791254 -7.8567876882) (40 . 0.0000000000) (41 . 0.0000000000) (42 . 0.0000000000) (91 . 0) (10 -931.2956645504 -8.1224731132) (40 . 0.0000000000) (41 . 0.0000000000) (42 . 0.1989123674) (91 . 0) (10 -931.4421111598 -8.4760265038) (40 . 0.0000000000) (41 . 0.0000000000) (42 . 0.0000000000) (91 . 0) (10 -931.4421111598 -20.1446556539) (40 . 0.0000000000) (41 . 0.0000000000) (42 . -0.4142135624) (91 . 0) (10 -931.9421111598 -20.6446556539) (40 . 0.0000000000) (41 . 0.0000000000) (42 . 0.0000000000) (91 . 0) (10 -933.9421111598 -20.6446556539) (40 . 0.0000000000) (41 . 0.0000000000) (42 . -0.4142135624) (91 . 0) (10 -934.4421111598 -20.1446556539) (40 . 0.0000000000) (41 . 0.0000000000) (42 . 0.0000000000) (91 . 0) (10 -934.4421111598 -15.6446556539) (40 . 0.0000000000) (41 . 0.0000000000) (42 . 0.4142135624) (91 . 0) (10 -934.9421111598 -15.1446556539) (40 . 0.0000000000) (41 . 0.0000000000) (42 . 0.0000000000) (91 . 0) (10 -935.1421111598 -15.1446556539) (40 . 0.0000000000) (41 . 0.0000000000) (42 . 0.4142135624) (91 . 0) (10 -935.6421111598 -15.6446556539) (40 . 0.0000000000) (41 . 0.0000000000) (42 . 0.0000000000) (91 . 0) (10 -935.6421111598 -21.6446556539) (40 . 0.0000000000) (41 . 0.0000000000) (42 . 0.4142135624) (91 . 0) (10 -935.1421111598 -22.1446556539) (40 . 0.0000000000) (41 . 0.0000000000) (42 . 0.0000000000) (91 . 0) (10 -918.9421111598 -22.1446556539) (40 . 0.0000000000) (41 . 0.0000000000) (42 . 0.4142135624) (91 . 0) (10 -918.4421111598 -21.6446556539) (40 . 0.0000000000) (41 . 0.0000000000) (42 . 0.0000000000) (91 . 0) (10 -918.4421111598 -19.7446556539) (40 . 0.0000000000) (41 . 0.0000000000) (42 . 0.4142135624) (91 . 0) (10 -918.9421111598 -19.2446556539) (40 . 0.0000000000) (41 . 0.0000000000) (42 . 0.0000000000) (91 . 0) (10 -921.1421111598 -19.2446556539) (40 . 0.0000000000) (41 . 0.0000000000) (42 . -0.4142135624) (91 . 0) (10 -921.6421111598 -18.7446556539) (40 . 0.0000000000) (41 . 0.0000000000) (42 . 0.0000000000) (91 . 0) (10 -921.6421111598 34.3553443461) (40 . 0.0000000000) (41 . 0.0000000000) (42 . 0.4142135624) (91 . 0) (10 -922.1421111598 34.8553443461) (40 . 0.0000000000) (41 . 0.0000000000) (42 . 0.4142135624) (91 . 0) (10 -922.6421111598 34.3553443461) (40 . 0.0000000000) (41 . 0.0000000000) (42 . 0.0000000000) (91 . 0) (10 -922.6421111598 31.3553443461) (40 . 0.0000000000) (41 . 0.0000000000) (42 . -0.4142135624) (91 . 0) (10 -923.1421111598 30.8553443461) (40 . 0.0000000000) (41 . 0.0000000000) (42 . 0.0000000000) (91 . 0) (10 -952.1421111598 30.8553443461) (40 . 0.0000000000) (41 . 0.0000000000) (42 . 0.4142135624) (91 . 0) (10 -952.6421111598 30.3553443461) (40 . 0.0000000000) (41 . 0.0000000000) (42 . 0.0000000000) (91 . 0) (10 -952.6421111598 29.8553443461) (40 . 0.0000000000) (41 . 0.0000000000) (42 . 0.4142135624) (91 . 0) (10 -952.1421111598 29.3553443461) (40 . 0.0000000000) (41 . 0.0000000000) (42 . 0.0000000000) (91 . 0) (10 -948.1421111598 29.3553443461) (40 . 0.0000000000) (41 . 0.0000000000) (42 . -0.4142135624) (91 . 0) (210 0.0000000000 0.0000000000 -1.0000000000))
((0 . "LINE") (100 . "AcDbEntity") (67 . 0) (8 . "A-Window") (62 . 6) (6 . "Continuous") (100 . "AcDbLine") (10 93.8677670258 43.0415554176 0.0000000000) (11 952.6421111598 43.0415554176 0.0000000000) (210 0.0000000000 0.0000000000 1.0000000000))
((0 . "LINE") (100 . "AcDbEntity") (67 . 0) (8 . "A-Window") (62 . 6) (6 . "Continuous") (100 . "AcDbLine") (10 93.8677670258 47.0415554176 0.0000000000) (11 952.6421111598 47.0415554176 0.0000000000) (210 0.0000000000 0.0000000000 1.0000000000))
((0 . "LWPOLYLINE") (100 . "AcDbEntity") (67 . 0) (8 . "A-Window") (62 . 151) (6 . "Continuous") (100 . "AcDbPolyline") (90 . 6) (70 . 0) (43 . 0.0000000000) (38 . 0.0000000000) (39 . 0.0000000000) (10 -93.8677670258 42.0415554176) (40 . 0.0000000000) (41 . 0.0000000000) (42 . 0.0000000000) (91 . 0) (10 -951.6421111598 42.0415554176) (40 . 0.0000000000) (41 . 0.0000000000) (42 . 0.0000000000) (91 . 0) (10 -952.6421111598 43.0415554176) (40 . 0.0000000000) (41 . 0.0000000000) (42 . 0.0000000000) (91 . 0) (10 -952.6421111598 47.0415554176) (40 . 0.0000000000) (41 . 0.0000000000) (42 . 0.0000000000) (91 . 0) (10 -951.6421111598 48.0415554176) (40 . 0.0000000000) (41 . 0.0000000000) (42 . 0.0000000000) (91 . 0) (10 -93.8677670258 48.0415554176) (40 . 0.0000000000) (41 . 0.0000000000) (42 . 0.0000000000) (91 . 0) (210 0.0000000000 0.0000000000 -1.0000000000))
((0 . "LWPOLYLINE") (100 . "AcDbEntity") (67 . 0) (8 . "A-Window") (62 . 151) (6 . "Continuous") (100 . "AcDbPolyline") (90 . 6) (70 . 0) (43 . 0.0000000000) (38 . 0.0000000000) (39 . 0.0000000000) (10 -93.8677670013 62.8553443461) (40 . 0.0000000000) (41 . 0.0000000000) (42 . 0.0000000000) (91 . 0) (10 -951.6421111598 62.8553443461) (40 . 0.0000000000) (41 . 0.0000000000) (42 . 0.0000000000) (91 . 0) (10 -952.6421111598 61.8553443461) (40 . 0.0000000000) (41 . 0.0000000000) (42 . 0.0000000000) (91 . 0) (10 -952.6421111598 57.8553443461) (40 . 0.0000000000) (41 . 0.0000000000) (42 . 0.0000000000) (91 . 0) (10 -951.6421111598 56.8553443461) (40 . 0.0000000000) (41 . 0.0000000000) (42 . 0.0000000000) (91 . 0) (10 -93.8677670013 56.8553443461) (40 . 0.0000000000) (41 . 0.0000000000) (42 . 0.0000000000) (91 . 0) (210 0.0000000000 0.0000000000 -1.0000000000))
((0 . "LINE") (100 . "AcDbEntity") (67 . 0) (8 . "A-Window") (62 . 6) (6 . "Continuous") (100 . "AcDbLine") (10 93.8677670013 57.8553443461 0.0000000000) (11 952.6421111598 57.8553443461 0.0000000000) (210 0.0000000000 0.0000000000 1.0000000000))
((0 . "LINE") (100 . "AcDbEntity") (67 . 0) (8 . "A-Window") (62 . 6) (6 . "Continuous") (100 . "AcDbLine") (10 93.8677670013 61.8549580744 0.0000000000) (11 952.6421111598 61.8549580744 0.0000000000) (210 0.0000000000 0.0000000000 1.0000000000))
((0 . "LINE") (100 . "AcDbEntity") (67 . 0) (8 . "A-Window") (62 . 151) (6 . "Continuous") (100 . "AcDbLine") (10 922.6421111598 30.8553443461 0.0000000000) (11 922.6421111598 38.8553443463 0.0000000000) (210 0.0000000000 0.0000000000 1.0000000000))
((0 . "LINE") (100 . "AcDbEntity") (67 . 0) (8 . "A-Window") (62 . 151) (6 . "Continuous") (100 . "AcDbLine") (10 938.6421111598 30.8553443461 0.0000000000) (11 922.6421111598 38.8553443463 0.0000000000) (210 0.0000000000 0.0000000000 1.0000000000))
((0 . "LINE") (100 . "AcDbEntity") (67 . 0) (8 . "A-Window") (62 . 151) (6 . "Continuous") (100 . "AcDbLine") (10 938.6421111598 38.8553443461 0.0000000000) (11 922.6421111598 30.8553443461 0.0000000000) (210 0.0000000000 0.0000000000 1.0000000000))
((0 . "LINE") (100 . "AcDbEntity") (67 . 0) (8 . "A-Window") (62 . 151) (6 . "Continuous") (100 . "AcDbLine") (10 922.6421111598 42.0415554178 0.0000000000) (11 952.6125882005 42.0415554176 0.0000000000) (210 0.0000000000 0.0000000000 1.0000000000))
((0 . "LINE") (100 . "AcDbEntity") (67 . 0) (8 . "A-Window") (62 . 151) (6 . "Continuous") (100 . "AcDbLine") (10 951.9550502026 30.8553443461 0.0000000000) (11 922.6421111598 30.8553443461 0.0000000000) (210 0.0000000000 0.0000000000 1.0000000000))
((0 . "LWPOLYLINE") (100 . "AcDbEntity") (67 . 0) (8 . "A-Window") (62 . 3) (6 . "Continuous") (100 . "AcDbPolyline") (90 . 44) (70 . 1) (43 . 0.0000000000) (38 . 0.0000000000) (39 . 0.0000000000) (10 961.8381452039 61.7129045678) (40 . 0.0000000000) (41 . 0.0000000000) (42 . 0.0441616864) (91 . 0) (10 968.5985110036 62.3258471632) (40 . 0.0000000000) (41 . 0.0000000000) (42 . 0.9363619320) (91 . 0) (10 968.3587692189 63.0283855080) (40 . 0.0000000000) (41 . 0.0000000000) (42 . -0.0548443031) (91 . 0) (10 962.0302780808 63.1010962817) (40 . 0.0000000000) (41 . 0.0000000000) (42 . 0.0302761843) (91 . 0) (10 961.9698919736 63.1047561584) (40 . 0.0000000000) (41 . 0.0000000000) (42 . 0.0000000000) (91 . 0) (10 955.0282711858 63.1047561584) (40 . 0.0000000000) (41 . 0.0000000000) (42 . 0.4142135624) (91 . 0) (10 954.5282711858 62.6047561584) (40 . 0.0000000000) (41 . 0.0000000000) (42 . 0.0000000000) (91 . 0) (10 954.5282711858 59.4047561584) (40 . 0.0000000000) (41 . 0.0000000000) (42 . 1.0000000000) (91 . 0) (10 955.5282711858 59.4047561584) (40 . 0.0000000000) (41 . 0.0000000000) (42 . 0.0000000000) (91 . 0) (10 955.5282711858 61.4047561584) (40 . 0.0000000000) (41 . 0.0000000000) (42 . -0.4142135624) (91 . 0) (10 956.0282711858 61.9047561584) (40 . 0.0000000000) (41 . 0.0000000000) (42 . 0.0000000000) (91 . 0) (10 959.8392221170 61.9047561584) (40 . 0.0000000000) (41 . 0.0000000000) (42 . -0.4142135624) (91 . 0) (10 960.1392221170 61.6047561584) (40 . 0.0000000000) (41 . 0.0000000000) (42 . 0.0000000000) (91 . 0) (10 960.1392221169 58.3553443460) (40 . 0.0000000000) (41 . 0.0000000000) (42 . -0.4142135624) (91 . 0) (10 959.9392221169 58.1553443460) (40 . 0.0000000000) (41 . 0.0000000000) (42 . 0.0000000000) (91 . 0) (10 958.9392221169 58.1553443462) (40 . 0.0000000000) (41 . 0.0000000000) (42 . -0.4142135623) (91 . 0) (10 958.7392221170 58.3553443462) (40 . 0.0000000000) (41 . 0.0000000000) (42 . 0.0000000000) (91 . 0) (10 958.7392221170 59.9053443461) (40 . 0.0000000000) (41 . 0.0000000000) (42 . 0.4142135624) (91 . 0) (10 958.2392221170 60.4053443461) (40 . 0.0000000000) (41 . 0.0000000000) (42 . 0.0000000000) (91 . 0) (10 957.8392221169 60.4053443461) (40 . 0.0000000000) (41 . 0.0000000000) (42 . 0.4142135624) (91 . 0) (10 957.3392221170 59.9053443461) (40 . 0.0000000000) (41 . 0.0000000000) (42 . 0.0000000000) (91 . 0) (10 957.3392221169 53.9053443461) (40 . 0.0000000000) (41 . 0.0000000000) (42 . 0.4142135624) (91 . 0) (10 957.8392221169 53.4053443461) (40 . 0.0000000000) (41 . 0.0000000000) (42 . 0.0000000000) (91 . 0) (10 958.2392221170 53.4053443461) (40 . 0.0000000000) (41 . 0.0000000000) (42 . 0.4142135624) (91 . 0) (10 958.7392221170 53.9053443461) (40 . 0.0000000000) (41 . 0.0000000000) (42 . 0.0000000000) (91 . 0) (10 958.7392221170 55.4553443461) (40 . 0.0000000000) (41 . 0.0000000000) (42 . -0.4142135624) (91 . 0) (10 958.9392221170 55.6553443461) (40 . 0.0000000000) (41 . 0.0000000000) (42 . 0.0000000000) (91 . 0) (10 959.9392221170 55.6553443462) (40 . 0.0000000000) (41 . 0.0000000000) (42 . -0.4142135624) (91 . 0) (10 960.1392221170 55.4553443461) (40 . 0.0000000000) (41 . 0.0000000000) (42 . 0.0000000000) (91 . 0) (10 960.1392221170 54.1047561584) (40 . 0.0000000000) (41 . 0.0000000000) (42 . 0.4142135624) (91 . 0) (10 960.4392221170 53.8047561584) (40 . 0.0000000000) (41 . 0.0000000000) (42 . 0.0000000000) (91 . 0) (10 962.3271560891 53.8047561584) (40 . 0.0000000000) (41 . 0.0000000000) (42 . 0.0120642717) (91 . 0) (10 962.3512740997 53.8053381756) (40 . 0.0000000000) (41 . 0.0000000000) (42 . 0.0000000000) (91 . 0) (10 968.0747392712 54.0817370999) (40 . 0.0000000000) (41 . 0.0000000000) (42 . 0.9528731560) (91 . 0) (10 968.0747392712 54.7809222759) (40 . 0.0000000000) (41 . 0.0000000000) (42 . 0.0000000000) (91 . 0) (10 961.8151041065 55.0832140474) (40 . 0.0000000000) (41 . 0.0000000000) (42 . -0.4001496687) (91 . 0) (10 961.3392221170 55.5826320302) (40 . 0.0000000000) (41 . 0.0000000000) (42 . 0.0000000000) (91 . 0) (10 961.3392221170 57.0104512349) (40 . 0.0000000000) (41 . 0.0000000000) (42 . -0.4001496687) (91 . 0) (10 961.8151041065 57.5098692178) (40 . 0.0000000000) (41 . 0.0000000000) (42 . 0.0000000000) (91 . 0) (10 968.0747392712 57.8121609893) (40 . 0.0000000000) (41 . 0.0000000000) (42 . 0.9528731560) (91 . 0) (10 968.0747392712 58.5113461653) (40 . 0.0000000000) (41 . 0.0000000000) (42 . 0.0000000000) (91 . 0) (10 961.8151041065 58.8136379368) (40 . 0.0000000000) (41 . 0.0000000000) (42 . -0.4001496687) (91 . 0) (10 961.3392221170 59.3130559196) (40 . 0.0000000000) (41 . 0.0000000000) (42 . 0.0000000000) (91 . 0) (10 961.3392221170 61.2129057276) (40 . 0.0000000000) (41 . 0.0000000000) (42 . -0.4135828614) (91 . 0) (210 0.0000000000 0.0000000000 1.0000000000))
((0 . "LWPOLYLINE") (100 . "AcDbEntity") (67 . 0) (8 . "A-Window") (62 . 151) (6 . "Continuous") (100 . "AcDbPolyline") (90 . 81) (70 . 1) (43 . 0.0000000000) (38 . 0.0000000000) (39 . 0.0000000000) (10 -955.4391721170 27.7553443461) (40 . 0.0000000000) (41 . 0.0000000000) (42 . 0.0000000000) (91 . 0) (10 -952.3421111598 27.7553443461) (40 . 0.0000000000) (41 . 0.0000000000) (42 . 0.4142135624) (91 . 0) (10 -952.1421111598 27.9553443461) (40 . 0.0000000000) (41 . 0.0000000000) (42 . 0.0000000000) (91 . 0) (10 -952.1421111598 29.1553443461) (40 . 0.0000000000) (41 . 0.0000000000) (42 . -0.4142135624) (91 . 0) (10 -951.9421111598 29.3553443461) (40 . 0.0000000000) (41 . 0.0000000000) (42 . 0.0000000000) (91 . 0) (10 -950.8421111598 29.3553443461) (40 . 0.0000000000) (41 . 0.0000000000) (42 . -0.4142135624) (91 . 0) (10 -950.6421111598 29.1553443461) (40 . 0.0000000000) (41 . 0.0000000000) (42 . 0.0000000000) (91 . 0) (10 -950.6421111598 26.9053443461) (40 . 0.0000000000) (41 . 0.0000000000) (42 . 0.4142135624) (91 . 0) (10 -950.4421111598 26.7053443461) (40 . 0.0000000000) (41 . 0.0000000000) (42 . 0.0000000000) (91 . 0) (10 -945.1421111598 26.7053443461) (40 . 0.0000000000) (41 . 0.0000000000) (42 . 0.4142135624) (91 . 0) (10 -944.8421111598 27.0053443461) (40 . 0.0000000000) (41 . 0.0000000000) (42 . 0.0000000000) (91 . 0) (10 -944.8421111598 27.7053443461) (40 . 0.0000000000) (41 . 0.0000000000) (42 . 0.4142135624) (91 . 0) (10 -945.1421111598 28.0053443461) (40 . 0.0000000000) (41 . 0.0000000000) (42 . 0.0000000000) (91 . 0) (10 -946.0421111598 28.0053443461) (40 . 0.0000000000) (41 . 0.0000000000) (42 . -0.4142135624) (91 . 0) (10 -946.3421111598 28.3053443461) (40 . 0.0000000000) (41 . 0.0000000000) (42 . 0.0000000000) (91 . 0) (10 -946.3421111598 28.9053443461) (40 . 0.0000000000) (41 . 0.0000000000) (42 . -0.4142135624) (91 . 0) (10 -946.0421111598 29.2053443461) (40 . 0.0000000000) (41 . 0.0000000000) (42 . 0.0000000000) (91 . 0) (10 -943.6421111598 29.2053443461) (40 . 0.0000000000) (41 . 0.0000000000) (42 . -0.4142135624) (91 . 0) (10 -943.3421111598 28.9053443461) (40 . 0.0000000000) (41 . 0.0000000000) (42 . 0.0000000000) (91 . 0) (10 -943.3421111598 27.0053443461) (40 . 0.0000000000) (41 . 0.0000000000) (42 . 0.4142135624) (91 . 0) (10 -943.0421111598 26.7053443461) (40 . 0.0000000000) (41 . 0.0000000000) (42 . 0.0000000000) (91 . 0) (10 -940.1421111598 26.7053443461) (40 . 0.0000000000) (41 . 0.0000000000) (42 . 0.4142135624) (91 . 0) (10 -939.8421111598 27.0053443461) (40 . 0.0000000000) (41 . 0.0000000000) (42 . 0.0000000000) (91 . 0) (10 -939.8421111598 29.0553443461) (40 . 0.0000000000) (41 . 0.0000000000) (42 . -0.4142135624) (91 . 0) (10 -939.5421111598 29.3553443461) (40 . 0.0000000000) (41 . 0.0000000000) (42 . 0.0000000000) (91 . 0) (10 -938.9421111598 29.3553443461) (40 . 0.0000000000) (41 . 0.0000000000) (42 . -0.4142135624) (91 . 0) (10 -938.6421111598 29.0553443461) (40 . 0.0000000000) (41 . 0.0000000000) (42 . 0.0000000000) (91 . 0) (10 -938.6421111598 25.5053443461) (40 . 0.0000000000) (41 . 0.0000000000) (42 . -0.4142135624) (91 . 0) (10 -938.9421111598 25.2053443461) (40 . 0.0000000000) (41 . 0.0000000000) (42 . 0.0000000000) (91 . 0) (10 -950.4421111598 25.2053443461) (40 . 0.0000000000) (41 . 0.0000000000) (42 . 0.4142135624) (91 . 0) (10 -950.6421111598 25.0053443461) (40 . 0.0000000000) (41 . 0.0000000000) (42 . 0.0000000000) (91 . 0) (10 -950.6421111598 24.3553443461) (40 . 0.0000000000) (41 . 0.0000000000) (42 . -0.4142135624) (91 . 0) (10 -951.1421111598 23.8553443461) (40 . 0.0000000000) (41 . 0.0000000000) (42 . 0.0000000000) (91 . 0) (10 -953.0421111598 23.8553443461) (40 . 0.0000000000) (41 . 0.0000000000) (42 . -0.4142135624) (91 . 0) (10 -953.3421111598 24.1553443461) (40 . 0.0000000000) (41 . 0.0000000000) (42 . 0.0000000000) (91 . 0) (10 -953.3421111598 24.5553443461) (40 . 0.0000000000) (41 . 0.0000000000) (42 . -0.4142135624) (91 . 0) (10 -953.0421111598 24.8553443461) (40 . 0.0000000000) (41 . 0.0000000000) (42 . 0.0000000000) (91 . 0) (10 -952.1421111598 24.8553443461) (40 . 0.0000000000) (41 . 0.0000000000) (42 . 0.4142135624) (91 . 0) (10 -951.8421111598 25.1553443461) (40 . 0.0000000000) (41 . 0.0000000000) (42 . 0.0000000000) (91 . 0) (10 -951.8421111598 25.7553443461) (40 . 0.0000000000) (41 . 0.0000000000) (42 . 0.4142135624) (91 . 0) (10 -952.3421111598 26.2553443461) (40 . 0.0000000000) (41 . 0.0000000000) (42 . 0.0000000000) (91 . 0) (10 -955.1421111598 26.2553443461) (40 . 0.0000000000) (41 . 0.0000000000) (42 . 0.0000000000) (91 . 0) (10 -957.9421111598 26.2553443461) (40 . 0.0000000000) (41 . 0.0000000000) (42 . 0.4142135624) (91 . 0) (10 -958.4421111598 25.7553443461) (40 . 0.0000000000) (41 . 0.0000000000) (42 . 0.0000000000) (91 . 0) (10 -958.4421111598 25.1553443461) (40 . 0.0000000000) (41 . 0.0000000000) (42 . 0.4142135624) (91 . 0) (10 -958.1421111598 24.8553443461) (40 . 0.0000000000) (41 . 0.0000000000) (42 . 0.0000000000) (91 . 0) (10 -957.2421111598 24.8553443461) (40 . 0.0000000000) (41 . 0.0000000000) (42 . -0.4142135624) (91 . 0) (10 -956.9421111598 24.5553443461) (40 . 0.0000000000) (41 . 0.0000000000) (42 . 0.0000000000) (91 . 0) (10 -956.9421111598 24.1553443461) (40 . 0.0000000000) (41 . 0.0000000000) (42 . -0.4142135624) (91 . 0) (10 -957.2421111598 23.8553443461) (40 . 0.0000000000) (41 . 0.0000000000) (42 . 0.0000000000) (91 . 0) (10 -959.1421111598 23.8553443461) (40 . 0.0000000000) (41 . 0.0000000000) (42 . -0.4142135624) (91 . 0) (10 -959.6421111598 24.3553443461) (40 . 0.0000000000) (41 . 0.0000000000) (42 . 0.0000000000) (91 . 0) (10 -959.6421111598 27.2553443461) (40 . 0.0000000000) (41 . 0.0000000000) (42 . -0.4142135624) (91 . 0) (10 -959.1421111598 27.7553443461) (40 . 0.0000000000) (41 . 0.0000000000) (42 . 0.0000000000) (91 . 0) (10 -958.1391721170 27.7553443461) (40 . 0.0000000000) (41 . 0.0000000000) (42 . 0.4142135624) (91 . 0) (10 -957.6391721170 28.2553443461) (40 . 0.0000000000) (41 . 0.0000000000) (42 . 0.0000000000) (91 . 0) (10 -957.6391721170 51.1553443461) (40 . 0.0000000000) (41 . 0.0000000000) (42 . 0.4142135624) (91 . 0) (10 -958.1391721170 51.6553443461) (40 . 0.0000000000) (41 . 0.0000000000) (42 . 0.0000000000) (91 . 0) (10 -959.5391721170 51.6553443461) (40 . 0.0000000000) (41 . 0.0000000000) (42 . -0.4142135624) (91 . 0) (10 -960.0391721170 52.1553443461) (40 . 0.0000000000) (41 . 0.0000000000) (42 . 0.0000000000) (91 . 0) (10 -960.0391721170 54.9553443463) (40 . 0.0000000000) (41 . 0.0000000000) (42 . -0.4142135624) (91 . 0) (10 -959.8391721170 55.1553443463) (40 . 0.0000000000) (41 . 0.0000000000) (42 . 0.0000000000) (91 . 0) (10 -959.2391721170 55.1553443463) (40 . 0.0000000000) (41 . 0.0000000000) (42 . -0.4142135624) (91 . 0) (10 -959.0391721170 54.9553443463) (40 . 0.0000000000) (41 . 0.0000000000) (42 . 0.0000000000) (91 . 0) (10 -959.0391721170 53.6552443461) (40 . 0.0000000000) (41 . 0.0000000000) (42 . 0.4142135624) (91 . 0) (10 -958.5392721170 53.1553443461) (40 . 0.0000000000) (41 . 0.0000000000) (42 . 0.0000000000) (91 . 0) (10 -957.5391721169 53.1553443461) (40 . 0.0000000000) (41 . 0.0000000000) (42 . 0.4142135624) (91 . 0) (10 -957.1391721170 53.5553443461) (40 . 0.0000000000) (41 . 0.0000000000) (42 . 0.0000000000) (91 . 0) (10 -957.1391721170 60.2553443461) (40 . 0.0000000000) (41 . 0.0000000000) (42 . 0.4142135624) (91 . 0) (10 -957.5391721170 60.6553443461) (40 . 0.0000000000) (41 . 0.0000000000) (42 . 0.0000000000) (91 . 0) (10 -958.5392721170 60.6553443461) (40 . 0.0000000000) (41 . 0.0000000000) (42 . 0.4142135624) (91 . 0) (10 -959.0391721169 60.1554443461) (40 . 0.0000000000) (41 . 0.0000000000) (42 . 0.0000000000) (91 . 0) (10 -959.0391721170 58.8553443460) (40 . 0.0000000000) (41 . 0.0000000000) (42 . -0.4142135624) (91 . 0) (10 -959.2391721170 58.6553443460) (40 . 0.0000000000) (41 . 0.0000000000) (42 . 0.0000000000) (91 . 0) (10 -959.8391721170 58.6553443460) (40 . 0.0000000000) (41 . 0.0000000000) (42 . -0.4142135624) (91 . 0) (10 -960.0391721170 58.8553443460) (40 . 0.0000000000) (41 . 0.0000000000) (42 . 0.0000000000) (91 . 0) (10 -960.0391721170 61.4553443461) (40 . 0.0000000000) (41 . 0.0000000000) (42 . -0.4142135624) (91 . 0) (10 -959.6391721170 61.8553443461) (40 . 0.0000000000) (41 . 0.0000000000) (42 . 0.0000000000) (91 . 0) (10 -956.0391721170 61.8553443461) (40 . 0.0000000000) (41 . 0.0000000000) (42 . -0.4142135624) (91 . 0) (10 -955.6391721170 61.4553443461) (40 . 0.0000000000) (41 . 0.0000000000) (42 . 0.0000000000) (91 . 0) (10 -955.6391721170 27.9553443461) (40 . 0.0000000000) (41 . 0.0000000000) (42 . 0.4142135624) (91 . 0) (210 0.0000000000 0.0000000000 -1.0000000000))
((0 . "LWPOLYLINE") (100 . "AcDbEntity") (67 . 0) (8 . "A-Window") (62 . 151) (6 . "Continuous") (100 . "AcDbPolyline") (90 . 2) (70 . 0) (43 . 0.0000000000) (38 . 0.0000000000) (39 . 0.0000000000) (10 -952.6421111598 38.8497574416) (40 . 0.0000000000) (41 . 0.0000000000) (42 . 0.0000000000) (91 . 0) (10 -952.6421111598 30.3553443461) (40 . 0.0000000000) (41 . 0.0000000000) (42 . 0.0000000000) (91 . 0) (210 0.0000000000 0.0000000000 -1.0000000000))
((0 . "LWPOLYLINE") (100 . "AcDbEntity") (67 . 0) (8 . "A-Window") (62 . 151) (6 . "Continuous") (100 . "AcDbPolyline") (90 . 2) (70 . 0) (43 . 0.0000000000) (38 . 0.0000000000) (39 . 0.0000000000) (10 -938.6421111598 30.8553443461) (40 . 0.0000000000) (41 . 0.0000000000) (42 . 0.0000000000) (91 . 0) (10 -938.6421111598 38.8553443461) (40 . 0.0000000000) (41 . 0.0000000000) (42 . 0.0000000000) (91 . 0) (210 0.0000000000 0.0000000000 -1.0000000000))
((0 . "ARC") (100 . "AcDbEntity") (67 . 0) (8 . "A-Window") (62 . 151) (6 . "Continuous") (100 . "AcDbCircle") (10 -952.1996071367 78.3974005148 0.0000000000) (40 . 15.5520516883) (210 0.0000000000 0.0000000000 -1.0000000000) (100 . "AcDbArc") (50 . -1.7536980501) (51 . -1.5349415434))
((0 . "LINE") (100 . "AcDbEntity") (67 . 0) (8 . "A-Window") (62 . 151) (6 . "Continuous") (100 . "AcDbLine") (10 952.6421111598 43.0415554176 0.0000000000) (11 955.6391721170 43.0415554176 0.0000000000) (210 0.0000000000 0.0000000000 1.0000000000))
((0 . "LINE") (100 . "AcDbEntity") (67 . 0) (8 . "A-Window") (62 . 151) (6 . "Continuous") (100 . "AcDbLine") (10 955.0282711858 58.9047561584 0.0000000000) (11 955.6391721170 58.9047561584 0.0000000000) (210 0.0000000000 0.0000000000 1.0000000000))
)
("VK_CuaDi"
((0 . "LINE") (100 . "AcDbEntity") (67 . 0) (8 . "A-Window") (62 . 8) (6 . "HIDDEN") (48 . 200.0000000000) (100 . "AcDbLine") (10 1632.8578888398 0.7496276428 0.0000000000) (11 998.4087703975 334.6450221887 0.0000000000) (210 0.0000000000 0.0000000000 1.0000000000))
((0 . "ARC") (100 . "AcDbEntity") (67 . 0) (8 . "A-Window") (62 . 8) (6 . "HIDDEN") (48 . 200.0000000000) (100 . "AcDbCircle") (10 -1213.4806704840 23.9172815797 0.0000000000) (40 . 377.8989957167) (210 0.0000000000 0.0000000000 -1.0000000000) (100 . "AcDbArc") (50 . -0.9653545850) (51 . 0.9653545850))
((0 . "LWPOLYLINE") (100 . "AcDbEntity") (67 . 0) (8 . "A-Window") (62 . 252) (420 . 9868950) (6 . "Continuous") (100 . "AcDbPolyline") (90 . 8) (70 . 1) (43 . 0.0000000000) (38 . 0.0000000000) (39 . 0.0000000000) (10 -1632.9627286882 4.9999999995) (40 . 0.0000000000) (41 . 0.0000000000) (42 . 0.0000000000) (91 . 0) (10 -1632.9627286882 -4.9999999996) (40 . 0.0000000000) (41 . 0.0000000000) (42 . 0.0000000000) (91 . 0) (10 -1631.9627286882 -5.9999999996) (40 . 0.0000000000) (41 . 0.0000000000) (42 . 0.0000000000) (91 . 0) (10 -836.8578888385 -5.6720844848) (40 . 0.0000000000) (41 . 0.0000000000) (42 . 0.0000000000) (91 . 0) (10 -835.8578888385 -4.6720844848) (40 . 0.0000000000) (41 . 0.0000000000) (42 . 0.0000000000) (91 . 0) (10 -835.8578888385 5.3279155143) (40 . 0.0000000000) (41 . 0.0000000000) (42 . 0.0000000000) (91 . 0) (10 -836.8578888385 6.3279155143) (40 . 0.0000000000) (41 . 0.0000000000) (42 . 0.0000000000) (91 . 0) (10 -1631.9627286882 5.9999999995) (40 . 0.0000000000) (41 . 0.0000000000) (42 . 0.0000000000) (91 . 0) (210 0.0000000000 0.0000000000 -1.0000000000))
((0 . "LINE") (100 . "AcDbEntity") (67 . 0) (8 . "A-Window") (62 . 8) (6 . "HIDDEN") (48 . 200.0000000000) (100 . "AcDbLine") (10 1632.8578888398 -0.7496276419 0.0000000000) (11 998.4087703975 -286.8104590285 0.0000000000) (210 0.0000000000 0.0000000000 1.0000000000))
((0 . "LINE") (100 . "AcDbEntity") (67 . 0) (8 . "A-Window") (62 . 2) (6 . "Continuous") (100 . "AcDbLine") (10 1551.3578888370 -7.9217121282 0.0000000000) (11 1632.8578888370 -7.9217121282 0.0000000000) (210 0.0000000000 0.0000000000 1.0000000000))
((0 . "LINE") (100 . "AcDbEntity") (67 . 0) (8 . "A-Window") (62 . 8) (6 . "CENTER") (48 . 0.5000000000) (100 . "AcDbLine") (10 1375.8578888383 -46.4217121280 0.0000000000) (11 1365.8578888383 -46.4217121280 0.0000000000) (210 0.0000000000 0.0000000000 1.0000000000))
((0 . "ARC") (100 . "AcDbEntity") (67 . 0) (8 . "A-Window") (62 . 252) (420 . 9868950) (6 . "Continuous") (100 . "AcDbCircle") (10 1369.8996278260 -45.4634511157 0.0000000000) (40 . 0.5832610123) (210 0.0000000000 0.0000000000 1.0000000000) (100 . "AcDbArc") (50 . -1.5707963268) (51 . 0.0000000000))
((0 . "ARC") (100 . "AcDbEntity") (67 . 0) (8 . "A-Window") (62 . 252) (420 . 9868950) (6 . "Continuous") (100 . "AcDbCircle") (10 1369.9596580464 -47.3166183160 0.0000000000) (40 . 0.5233603650) (210 0.0000000000 0.0000000000 1.0000000000) (100 . "AcDbArc") (50 . 0.0222526151) (51 . 1.6857508410))
((0 . "CIRCLE") (100 . "AcDbEntity") (67 . 0) (8 . "A-Window") (62 . 252) (420 . 9868950) (6 . "Continuous") (100 . "AcDbCircle") (10 1370.8578888383 -46.4217121280 0.0000000000) (40 . 4.0000000000) (210 0.0000000000 0.0000000000 1.0000000000))
((0 . "LINE") (100 . "AcDbEntity") (67 . 0) (8 . "A-Window") (62 . 8) (6 . "CENTER") (48 . 0.5000000000) (100 . "AcDbLine") (10 1370.8578888383 -41.4217121280 0.0000000000) (11 1370.8578888383 -51.4217121280 0.0000000000) (210 0.0000000000 0.0000000000 1.0000000000))
((0 . "LINE") (100 . "AcDbEntity") (67 . 0) (8 . "A-Window") (62 . 252) (420 . 9868950) (6 . "Continuous") (100 . "AcDbLine") (10 1370.4828888383 -47.3049731404 0.0000000000) (11 1370.4828888383 -49.3380171897 0.0000000000) (210 0.0000000000 0.0000000000 1.0000000000))
((0 . "LINE") (100 . "AcDbEntity") (67 . 0) (8 . "A-Window") (62 . 252) (420 . 9868950) (6 . "Continuous") (100 . "AcDbLine") (10 1373.7741939000 -46.0467121280 0.0000000000) (11 1373.7741939000 -46.7967121280 0.0000000000) (210 0.0000000000 0.0000000000 1.0000000000))
((0 . "ARC") (100 . "AcDbEntity") (67 . 0) (8 . "A-Window") (62 . 252) (420 . 9868950) (6 . "Continuous") (100 . "AcDbCircle") (10 1371.7597393684 -45.5172243919 0.0000000000) (40 . 0.5295876191) (210 0.0000000000 0.0000000000 1.0000000000) (100 . "AcDbArc") (50 . 3.0398793474) (51 . -1.5902185321))
((0 . "LINE") (100 . "AcDbEntity") (67 . 0) (8 . "A-Window") (62 . 252) (420 . 9868950) (6 . "Continuous") (100 . "AcDbLine") (10 1373.7741939000 -46.0467121280 0.0000000000) (11 1371.7494542556 -46.0467121280 0.0000000000) (210 0.0000000000 0.0000000000 1.0000000000))
((0 . "ARC") (100 . "AcDbEntity") (67 . 0) (8 . "A-Window") (62 . 252) (420 . 9868950) (6 . "Continuous") (100 . "AcDbCircle") (10 1371.7007738104 -47.2638695594 0.0000000000) (40 . 0.4696869718) (210 0.0000000000 0.0000000000 1.0000000000) (100 . "AcDbArc") (50 . 1.4669654186) (51 . -3.0539678520))
((0 . "LINE") (100 . "AcDbEntity") (67 . 0) (8 . "A-Window") (62 . 252) (420 . 9868950) (6 . "Continuous") (100 . "AcDbLine") (10 1373.7741939000 -46.7967121280 0.0000000000) (11 1371.7494542556 -46.7967121280 0.0000000000) (210 0.0000000000 0.0000000000 1.0000000000))
((0 . "LINE") (100 . "AcDbEntity") (67 . 0) (8 . "A-Window") (62 . 252) (420 . 9868950) (6 . "Continuous") (100 . "AcDbLine") (10 1371.2328888383 -47.3049731404 0.0000000000) (11 1371.2328888383 -49.3380171897 0.0000000000) (210 0.0000000000 0.0000000000 1.0000000000))
((0 . "LINE") (100 . "AcDbEntity") (67 . 0) (8 . "A-Window") (62 . 252) (420 . 9868950) (6 . "Continuous") (100 . "AcDbLine") (10 1371.2328888383 -49.3380171897 0.0000000000) (11 1370.4828888383 -49.3380171897 0.0000000000) (210 0.0000000000 0.0000000000 1.0000000000))
((0 . "LINE") (100 . "AcDbEntity") (67 . 0) (8 . "A-Window") (62 . 252) (420 . 9868950) (6 . "Continuous") (100 . "AcDbLine") (10 1371.2328888383 -43.5054070663 0.0000000000) (11 1370.4828888383 -43.5054070663 0.0000000000) (210 0.0000000000 0.0000000000 1.0000000000))
((0 . "LINE") (100 . "AcDbEntity") (67 . 0) (8 . "A-Window") (62 . 252) (420 . 9868950) (6 . "Continuous") (100 . "AcDbLine") (10 1370.4828888383 -43.5054070663 0.0000000000) (11 1370.4828888383 -45.4634511157 0.0000000000) (210 0.0000000000 0.0000000000 1.0000000000))
((0 . "LINE") (100 . "AcDbEntity") (67 . 0) (8 . "A-Window") (62 . 252) (420 . 9868950) (6 . "Continuous") (100 . "AcDbLine") (10 1371.2328888383 -43.5054070663 0.0000000000) (11 1371.2328888383 -45.4634511157 0.0000000000) (210 0.0000000000 0.0000000000 1.0000000000))
((0 . "LINE") (100 . "AcDbEntity") (67 . 0) (8 . "A-Window") (62 . 252) (420 . 9868950) (6 . "Continuous") (100 . "AcDbLine") (10 1367.9415837766 -46.0467121280 0.0000000000) (11 1367.9415837766 -46.7967121280 0.0000000000) (210 0.0000000000 0.0000000000 1.0000000000))
((0 . "LINE") (100 . "AcDbEntity") (67 . 0) (8 . "A-Window") (62 . 252) (420 . 9868950) (6 . "Continuous") (100 . "AcDbLine") (10 1369.8996278260 -46.0467121280 0.0000000000) (11 1367.9415837766 -46.0467121280 0.0000000000) (210 0.0000000000 0.0000000000 1.0000000000))
((0 . "LINE") (100 . "AcDbEntity") (67 . 0) (8 . "A-Window") (62 . 252) (420 . 9868950) (6 . "Continuous") (100 . "AcDbLine") (10 1369.8996278260 -46.7967121280 0.0000000000) (11 1367.9415837766 -46.7967121280 0.0000000000) (210 0.0000000000 0.0000000000 1.0000000000))
((0 . "LWPOLYLINE") (100 . "AcDbEntity") (67 . 0) (8 . "A-Window") (62 . 252) (420 . 9868950) (6 . "Continuous") (100 . "AcDbPolyline") (90 . 4) (70 . 1) (43 . 0.0000000000) (38 . 0.0000000000) (39 . 0.0000000000) (10 1632.8578888398 -61.4217121280) (40 . 0.0000000000) (41 . 0.0000000000) (42 . 0.0000000000) (91 . 0) (10 1340.8578888383 -61.4217121280) (40 . 0.0000000000) (41 . 0.0000000000) (42 . 0.0000000000) (91 . 0) (10 1340.8578888383 60.5782878720) (40 . 0.0000000000) (41 . 0.0000000000) (42 . 0.0000000000) (91 . 0) (10 1632.8578888398 60.5782878720) (40 . 0.0000000000) (41 . 0.0000000000) (42 . 0.0000000000) (91 . 0) (210 0.0000000000 0.0000000000 1.0000000000))
((0 . "LINE") (100 . "AcDbEntity") (67 . 0) (8 . "A-Window") (62 . 8) (6 . "CENTER") (48 . 0.5000000000) (100 . "AcDbLine") (10 1375.8578888383 45.5782878720 0.0000000000) (11 1365.8578888383 45.5782878720 0.0000000000) (210 0.0000000000 0.0000000000 1.0000000000))
((0 . "ARC") (100 . "AcDbEntity") (67 . 0) (8 . "A-Window") (62 . 252) (420 . 9868950) (6 . "Continuous") (100 . "AcDbCircle") (10 -1369.8996278260 44.6200268596 0.0000000000) (40 . 0.5832610123) (210 0.0000000000 0.0000000000 -1.0000000000) (100 . "AcDbArc") (50 . 1.5707963268) (51 . -3.1415926536))
((0 . "ARC") (100 . "AcDbEntity") (67 . 0) (8 . "A-Window") (62 . 252) (420 . 9868950) (6 . "Continuous") (100 . "AcDbCircle") (10 -1369.9596580464 46.4731940600 0.0000000000) (40 . 0.5233603650) (210 0.0000000000 0.0000000000 -1.0000000000) (100 . "AcDbArc") (50 . -3.1193400384) (51 . -1.4558418125))
((0 . "CIRCLE") (100 . "AcDbEntity") (67 . 0) (8 . "A-Window") (62 . 252) (420 . 9868950) (6 . "Continuous") (100 . "AcDbCircle") (10 -1370.8578888383 45.5782878720 0.0000000000) (40 . 4.0000000000) (210 0.0000000000 0.0000000000 -1.0000000000))
((0 . "LINE") (100 . "AcDbEntity") (67 . 0) (8 . "A-Window") (62 . 8) (6 . "CENTER") (48 . 0.5000000000) (100 . "AcDbLine") (10 1370.8578888383 40.5782878720 0.0000000000) (11 1370.8578888383 50.5782878720 0.0000000000) (210 0.0000000000 0.0000000000 1.0000000000))
((0 . "LINE") (100 . "AcDbEntity") (67 . 0) (8 . "A-Window") (62 . 252) (420 . 9868950) (6 . "Continuous") (100 . "AcDbLine") (10 1370.4828888383 46.4615488843 0.0000000000) (11 1370.4828888383 48.4945929337 0.0000000000) (210 0.0000000000 0.0000000000 1.0000000000))
((0 . "LINE") (100 . "AcDbEntity") (67 . 0) (8 . "A-Window") (62 . 252) (420 . 9868950) (6 . "Continuous") (100 . "AcDbLine") (10 1373.7741939000 45.2032878720 0.0000000000) (11 1373.7741939000 45.9532878720 0.0000000000) (210 0.0000000000 0.0000000000 1.0000000000))
((0 . "ARC") (100 . "AcDbEntity") (67 . 0) (8 . "A-Window") (62 . 252) (420 . 9868950) (6 . "Continuous") (100 . "AcDbCircle") (10 -1371.7597393684 44.6738001358 0.0000000000) (40 . 0.5295876191) (210 0.0000000000 0.0000000000 -1.0000000000) (100 . "AcDbArc") (50 . -0.1017133062) (51 . 1.5513741215))
((0 . "LINE") (100 . "AcDbEntity") (67 . 0) (8 . "A-Window") (62 . 252) (420 . 9868950) (6 . "Continuous") (100 . "AcDbLine") (10 1373.7741939000 45.2032878720 0.0000000000) (11 1371.7494542556 45.2032878720 0.0000000000) (210 0.0000000000 0.0000000000 1.0000000000))
((0 . "ARC") (100 . "AcDbEntity") (67 . 0) (8 . "A-Window") (62 . 252) (420 . 9868950) (6 . "Continuous") (100 . "AcDbCircle") (10 -1371.7007738104 46.4204453034 0.0000000000) (40 . 0.4696869718) (210 0.0000000000 0.0000000000 -1.0000000000) (100 . "AcDbArc") (50 . -1.6746272350) (51 . 0.0876248016))
((0 . "LINE") (100 . "AcDbEntity") (67 . 0) (8 . "A-Window") (62 . 252) (420 . 9868950) (6 . "Continuous") (100 . "AcDbLine") (10 1373.7741939000 45.9532878720 0.0000000000) (11 1371.7494542556 45.9532878720 0.0000000000) (210 0.0000000000 0.0000000000 1.0000000000))
((0 . "LINE") (100 . "AcDbEntity") (67 . 0) (8 . "A-Window") (62 . 252) (420 . 9868950) (6 . "Continuous") (100 . "AcDbLine") (10 1371.2328888383 46.4615488843 0.0000000000) (11 1371.2328888383 48.4945929337 0.0000000000) (210 0.0000000000 0.0000000000 1.0000000000))
((0 . "LINE") (100 . "AcDbEntity") (67 . 0) (8 . "A-Window") (62 . 252) (420 . 9868950) (6 . "Continuous") (100 . "AcDbLine") (10 1371.2328888383 48.4945929337 0.0000000000) (11 1370.4828888383 48.4945929337 0.0000000000) (210 0.0000000000 0.0000000000 1.0000000000))
((0 . "LINE") (100 . "AcDbEntity") (67 . 0) (8 . "A-Window") (62 . 252) (420 . 9868950) (6 . "Continuous") (100 . "AcDbLine") (10 1371.2328888383 42.6619828103 0.0000000000) (11 1370.4828888383 42.6619828103 0.0000000000) (210 0.0000000000 0.0000000000 1.0000000000))
((0 . "LINE") (100 . "AcDbEntity") (67 . 0) (8 . "A-Window") (62 . 252) (420 . 9868950) (6 . "Continuous") (100 . "AcDbLine") (10 1370.4828888383 42.6619828103 0.0000000000) (11 1370.4828888383 44.6200268596 0.0000000000) (210 0.0000000000 0.0000000000 1.0000000000))
((0 . "LINE") (100 . "AcDbEntity") (67 . 0) (8 . "A-Window") (62 . 252) (420 . 9868950) (6 . "Continuous") (100 . "AcDbLine") (10 1371.2328888383 42.6619828103 0.0000000000) (11 1371.2328888383 44.6200268596 0.0000000000) (210 0.0000000000 0.0000000000 1.0000000000))
((0 . "LINE") (100 . "AcDbEntity") (67 . 0) (8 . "A-Window") (62 . 252) (420 . 9868950) (6 . "Continuous") (100 . "AcDbLine") (10 1367.9415837766 45.2032878720 0.0000000000) (11 1367.9415837766 45.9532878720 0.0000000000) (210 0.0000000000 0.0000000000 1.0000000000))
((0 . "LINE") (100 . "AcDbEntity") (67 . 0) (8 . "A-Window") (62 . 252) (420 . 9868950) (6 . "Continuous") (100 . "AcDbLine") (10 1369.8996278260 45.2032878720 0.0000000000) (11 1367.9415837766 45.2032878720 0.0000000000) (210 0.0000000000 0.0000000000 1.0000000000))
((0 . "LINE") (100 . "AcDbEntity") (67 . 0) (8 . "A-Window") (62 . 252) (420 . 9868950) (6 . "Continuous") (100 . "AcDbLine") (10 1369.8996278260 45.9532878720 0.0000000000) (11 1367.9415837766 45.9532878720 0.0000000000) (210 0.0000000000 0.0000000000 1.0000000000))
((0 . "LINE") (100 . "AcDbEntity") (67 . 0) (8 . "A-Window") (62 . 8) (6 . "CENTER") (48 . 0.5000000000) (100 . "AcDbLine") (10 1602.8578888398 -46.4217121280 0.0000000000) (11 1612.8578888398 -46.4217121280 0.0000000000) (210 0.0000000000 0.0000000000 1.0000000000))
((0 . "ARC") (100 . "AcDbEntity") (67 . 0) (8 . "A-Window") (62 . 252) (420 . 9868950) (6 . "Continuous") (100 . "AcDbCircle") (10 -1608.8161498521 -45.4634511157 0.0000000000) (40 . 0.5832610123) (210 0.0000000000 0.0000000000 -1.0000000000) (100 . "AcDbArc") (50 . -1.5707963268) (51 . 0.0000000000))
((0 . "ARC") (100 . "AcDbEntity") (67 . 0) (8 . "A-Window") (62 . 252) (420 . 9868950) (6 . "Continuous") (100 . "AcDbCircle") (10 -1608.7561196317 -47.3166183160 0.0000000000) (40 . 0.5233603650) (210 0.0000000000 0.0000000000 -1.0000000000) (100 . "AcDbArc") (50 . 0.0222526151) (51 . 1.6857508410))
((0 . "CIRCLE") (100 . "AcDbEntity") (67 . 0) (8 . "A-Window") (62 . 252) (420 . 9868950) (6 . "Continuous") (100 . "AcDbCircle") (10 -1607.8578888398 -46.4217121280 0.0000000000) (40 . 4.0000000000) (210 0.0000000000 0.0000000000 -1.0000000000))
((0 . "LINE") (100 . "AcDbEntity") (67 . 0) (8 . "A-Window") (62 . 8) (6 . "CENTER") (48 . 0.5000000000) (100 . "AcDbLine") (10 1607.8578888398 -41.4217121280 0.0000000000) (11 1607.8578888398 -51.4217121280 0.0000000000) (210 0.0000000000 0.0000000000 1.0000000000))
((0 . "LINE") (100 . "AcDbEntity") (67 . 0) (8 . "A-Window") (62 . 252) (420 . 9868950) (6 . "Continuous") (100 . "AcDbLine") (10 1608.2328888398 -47.3049731404 0.0000000000) (11 1608.2328888398 -49.3380171897 0.0000000000) (210 0.0000000000 0.0000000000 1.0000000000))
((0 . "LINE") (100 . "AcDbEntity") (67 . 0) (8 . "A-Window") (62 . 252) (420 . 9868950) (6 . "Continuous") (100 . "AcDbLine") (10 1604.9415837781 -46.0467121280 0.0000000000) (11 1604.9415837781 -46.7967121280 0.0000000000) (210 0.0000000000 0.0000000000 1.0000000000))
((0 . "ARC") (100 . "AcDbEntity") (67 . 0) (8 . "A-Window") (62 . 252) (420 . 9868950) (6 . "Continuous") (100 . "AcDbCircle") (10 -1606.9560383097 -45.5172243919 0.0000000000) (40 . 0.5295876191) (210 0.0000000000 0.0000000000 -1.0000000000) (100 . "AcDbArc") (50 . 3.0398793474) (51 . -1.5902185321))
((0 . "LINE") (100 . "AcDbEntity") (67 . 0) (8 . "A-Window") (62 . 252) (420 . 9868950) (6 . "Continuous") (100 . "AcDbLine") (10 1604.9415837781 -46.0467121280 0.0000000000) (11 1606.9663234225 -46.0467121280 0.0000000000) (210 0.0000000000 0.0000000000 1.0000000000))
((0 . "ARC") (100 . "AcDbEntity") (67 . 0) (8 . "A-Window") (62 . 252) (420 . 9868950) (6 . "Continuous") (100 . "AcDbCircle") (10 -1607.0150038678 -47.2638695594 0.0000000000) (40 . 0.4696869718) (210 0.0000000000 0.0000000000 -1.0000000000) (100 . "AcDbArc") (50 . 1.4669654186) (51 . -3.0539678520))
((0 . "LINE") (100 . "AcDbEntity") (67 . 0) (8 . "A-Window") (62 . 252) (420 . 9868950) (6 . "Continuous") (100 . "AcDbLine") (10 1604.9415837781 -46.7967121280 0.0000000000) (11 1606.9663234225 -46.7967121280 0.0000000000) (210 0.0000000000 0.0000000000 1.0000000000))
((0 . "LINE") (100 . "AcDbEntity") (67 . 0) (8 . "A-Window") (62 . 252) (420 . 9868950) (6 . "Continuous") (100 . "AcDbLine") (10 1607.4828888398 -47.3049731404 0.0000000000) (11 1607.4828888398 -49.3380171897 0.0000000000) (210 0.0000000000 0.0000000000 1.0000000000))
((0 . "LINE") (100 . "AcDbEntity") (67 . 0) (8 . "A-Window") (62 . 252) (420 . 9868950) (6 . "Continuous") (100 . "AcDbLine") (10 1607.4828888398 -49.3380171897 0.0000000000) (11 1608.2328888398 -49.3380171897 0.0000000000) (210 0.0000000000 0.0000000000 1.0000000000))
((0 . "LINE") (100 . "AcDbEntity") (67 . 0) (8 . "A-Window") (62 . 252) (420 . 9868950) (6 . "Continuous") (100 . "AcDbLine") (10 1607.4828888398 -43.5054070663 0.0000000000) (11 1608.2328888398 -43.5054070663 0.0000000000) (210 0.0000000000 0.0000000000 1.0000000000))
((0 . "LINE") (100 . "AcDbEntity") (67 . 0) (8 . "A-Window") (62 . 252) (420 . 9868950) (6 . "Continuous") (100 . "AcDbLine") (10 1608.2328888398 -43.5054070663 0.0000000000) (11 1608.2328888398 -45.4634511157 0.0000000000) (210 0.0000000000 0.0000000000 1.0000000000))
((0 . "LINE") (100 . "AcDbEntity") (67 . 0) (8 . "A-Window") (62 . 252) (420 . 9868950) (6 . "Continuous") (100 . "AcDbLine") (10 1607.4828888398 -43.5054070663 0.0000000000) (11 1607.4828888398 -45.4634511157 0.0000000000) (210 0.0000000000 0.0000000000 1.0000000000))
((0 . "LINE") (100 . "AcDbEntity") (67 . 0) (8 . "A-Window") (62 . 252) (420 . 9868950) (6 . "Continuous") (100 . "AcDbLine") (10 1610.7741939015 -46.0467121280 0.0000000000) (11 1610.7741939015 -46.7967121280 0.0000000000) (210 0.0000000000 0.0000000000 1.0000000000))
((0 . "LINE") (100 . "AcDbEntity") (67 . 0) (8 . "A-Window") (62 . 252) (420 . 9868950) (6 . "Continuous") (100 . "AcDbLine") (10 1608.8161498521 -46.0467121280 0.0000000000) (11 1610.7741939015 -46.0467121280 0.0000000000) (210 0.0000000000 0.0000000000 1.0000000000))
((0 . "LINE") (100 . "AcDbEntity") (67 . 0) (8 . "A-Window") (62 . 252) (420 . 9868950) (6 . "Continuous") (100 . "AcDbLine") (10 1608.8161498521 -46.7967121280 0.0000000000) (11 1610.7741939015 -46.7967121280 0.0000000000) (210 0.0000000000 0.0000000000 1.0000000000))
((0 . "LINE") (100 . "AcDbEntity") (67 . 0) (8 . "A-Window") (62 . 8) (6 . "CENTER") (48 . 0.5000000000) (100 . "AcDbLine") (10 1602.8578888398 45.5782878720 0.0000000000) (11 1612.8578888398 45.5782878720 0.0000000000) (210 0.0000000000 0.0000000000 1.0000000000))
((0 . "ARC") (100 . "AcDbEntity") (67 . 0) (8 . "A-Window") (62 . 252) (420 . 9868950) (6 . "Continuous") (100 . "AcDbCircle") (10 1608.8161498521 44.6200268596 0.0000000000) (40 . 0.5832610123) (210 0.0000000000 0.0000000000 1.0000000000) (100 . "AcDbArc") (50 . 1.5707963268) (51 . 3.1415926536))
((0 . "ARC") (100 . "AcDbEntity") (67 . 0) (8 . "A-Window") (62 . 252) (420 . 9868950) (6 . "Continuous") (100 . "AcDbCircle") (10 1608.7561196317 46.4731940600 0.0000000000) (40 . 0.5233603650) (210 0.0000000000 0.0000000000 1.0000000000) (100 . "AcDbArc") (50 . -3.1193400384) (51 . -1.4558418125))
((0 . "CIRCLE") (100 . "AcDbEntity") (67 . 0) (8 . "A-Window") (62 . 252) (420 . 9868950) (6 . "Continuous") (100 . "AcDbCircle") (10 1607.8578888398 45.5782878720 0.0000000000) (40 . 4.0000000000) (210 0.0000000000 0.0000000000 1.0000000000))
((0 . "LINE") (100 . "AcDbEntity") (67 . 0) (8 . "A-Window") (62 . 8) (6 . "CENTER") (48 . 0.5000000000) (100 . "AcDbLine") (10 1607.8578888398 40.5782878720 0.0000000000) (11 1607.8578888398 50.5782878720 0.0000000000) (210 0.0000000000 0.0000000000 1.0000000000))
((0 . "LINE") (100 . "AcDbEntity") (67 . 0) (8 . "A-Window") (62 . 252) (420 . 9868950) (6 . "Continuous") (100 . "AcDbLine") (10 1608.2328888398 46.4615488843 0.0000000000) (11 1608.2328888398 48.4945929337 0.0000000000) (210 0.0000000000 0.0000000000 1.0000000000))
((0 . "LINE") (100 . "AcDbEntity") (67 . 0) (8 . "A-Window") (62 . 252) (420 . 9868950) (6 . "Continuous") (100 . "AcDbLine") (10 1604.9415837781 45.2032878720 0.0000000000) (11 1604.9415837781 45.9532878720 0.0000000000) (210 0.0000000000 0.0000000000 1.0000000000))
((0 . "ARC") (100 . "AcDbEntity") (67 . 0) (8 . "A-Window") (62 . 252) (420 . 9868950) (6 . "Continuous") (100 . "AcDbCircle") (10 1606.9560383097 44.6738001358 0.0000000000) (40 . 0.5295876191) (210 0.0000000000 0.0000000000 1.0000000000) (100 . "AcDbArc") (50 . -0.1017133062) (51 . 1.5513741215))
((0 . "LINE") (100 . "AcDbEntity") (67 . 0) (8 . "A-Window") (62 . 252) (420 . 9868950) (6 . "Continuous") (100 . "AcDbLine") (10 1604.9415837781 45.2032878720 0.0000000000) (11 1606.9663234225 45.2032878720 0.0000000000) (210 0.0000000000 0.0000000000 1.0000000000))
((0 . "ARC") (100 . "AcDbEntity") (67 . 0) (8 . "A-Window") (62 . 252) (420 . 9868950) (6 . "Continuous") (100 . "AcDbCircle") (10 1607.0150038678 46.4204453034 0.0000000000) (40 . 0.4696869718) (210 0.0000000000 0.0000000000 1.0000000000) (100 . "AcDbArc") (50 . -1.6746272350) (51 . 0.0876248016))
((0 . "LINE") (100 . "AcDbEntity") (67 . 0) (8 . "A-Window") (62 . 252) (420 . 9868950) (6 . "Continuous") (100 . "AcDbLine") (10 1604.9415837781 45.9532878720 0.0000000000) (11 1606.9663234225 45.9532878720 0.0000000000) (210 0.0000000000 0.0000000000 1.0000000000))
((0 . "LINE") (100 . "AcDbEntity") (67 . 0) (8 . "A-Window") (62 . 252) (420 . 9868950) (6 . "Continuous") (100 . "AcDbLine") (10 1607.4828888398 46.4615488843 0.0000000000) (11 1607.4828888398 48.4945929337 0.0000000000) (210 0.0000000000 0.0000000000 1.0000000000))
((0 . "LINE") (100 . "AcDbEntity") (67 . 0) (8 . "A-Window") (62 . 252) (420 . 9868950) (6 . "Continuous") (100 . "AcDbLine") (10 1607.4828888398 48.4945929337 0.0000000000) (11 1608.2328888398 48.4945929337 0.0000000000) (210 0.0000000000 0.0000000000 1.0000000000))
((0 . "LINE") (100 . "AcDbEntity") (67 . 0) (8 . "A-Window") (62 . 252) (420 . 9868950) (6 . "Continuous") (100 . "AcDbLine") (10 1607.4828888398 42.6619828103 0.0000000000) (11 1608.2328888398 42.6619828103 0.0000000000) (210 0.0000000000 0.0000000000 1.0000000000))
((0 . "LINE") (100 . "AcDbEntity") (67 . 0) (8 . "A-Window") (62 . 252) (420 . 9868950) (6 . "Continuous") (100 . "AcDbLine") (10 1608.2328888398 42.6619828103 0.0000000000) (11 1608.2328888398 44.6200268596 0.0000000000) (210 0.0000000000 0.0000000000 1.0000000000))
((0 . "LINE") (100 . "AcDbEntity") (67 . 0) (8 . "A-Window") (62 . 252) (420 . 9868950) (6 . "Continuous") (100 . "AcDbLine") (10 1607.4828888398 42.6619828103 0.0000000000) (11 1607.4828888398 44.6200268596 0.0000000000) (210 0.0000000000 0.0000000000 1.0000000000))
((0 . "LINE") (100 . "AcDbEntity") (67 . 0) (8 . "A-Window") (62 . 252) (420 . 9868950) (6 . "Continuous") (100 . "AcDbLine") (10 1610.7741939015 45.2032878720 0.0000000000) (11 1610.7741939015 45.9532878720 0.0000000000) (210 0.0000000000 0.0000000000 1.0000000000))
((0 . "LINE") (100 . "AcDbEntity") (67 . 0) (8 . "A-Window") (62 . 252) (420 . 9868950) (6 . "Continuous") (100 . "AcDbLine") (10 1608.8161498521 45.2032878720 0.0000000000) (11 1610.7741939015 45.2032878720 0.0000000000) (210 0.0000000000 0.0000000000 1.0000000000))
((0 . "LINE") (100 . "AcDbEntity") (67 . 0) (8 . "A-Window") (62 . 252) (420 . 9868950) (6 . "Continuous") (100 . "AcDbLine") (10 1608.8161498521 45.9532878720 0.0000000000) (11 1610.7741939015 45.9532878720 0.0000000000) (210 0.0000000000 0.0000000000 1.0000000000))
((0 . "LINE") (100 . "AcDbEntity") (67 . 0) (8 . "A-Window") (62 . 8) (6 . "CENTER") (48 . 0.5000000000) (100 . "AcDbLine") (10 1527.8578888398 -46.4217121280 0.0000000000) (11 1537.8578888398 -46.4217121280 0.0000000000) (210 0.0000000000 0.0000000000 1.0000000000))
((0 . "ARC") (100 . "AcDbEntity") (67 . 0) (8 . "A-Window") (62 . 252) (420 . 9868950) (6 . "Continuous") (100 . "AcDbCircle") (10 -1533.8161498521 -45.4634511157 0.0000000000) (40 . 0.5832610123) (210 0.0000000000 0.0000000000 -1.0000000000) (100 . "AcDbArc") (50 . -1.5707963268) (51 . 0.0000000000))
((0 . "ARC") (100 . "AcDbEntity") (67 . 0) (8 . "A-Window") (62 . 252) (420 . 9868950) (6 . "Continuous") (100 . "AcDbCircle") (10 -1533.7561196317 -47.3166183160 0.0000000000) (40 . 0.5233603650) (210 0.0000000000 0.0000000000 -1.0000000000) (100 . "AcDbArc") (50 . 0.0222526151) (51 . 1.6857508410))
((0 . "CIRCLE") (100 . "AcDbEntity") (67 . 0) (8 . "A-Window") (62 . 252) (420 . 9868950) (6 . "Continuous") (100 . "AcDbCircle") (10 -1532.8578888398 -46.4217121280 0.0000000000) (40 . 4.0000000000) (210 0.0000000000 0.0000000000 -1.0000000000))
((0 . "LINE") (100 . "AcDbEntity") (67 . 0) (8 . "A-Window") (62 . 8) (6 . "CENTER") (48 . 0.5000000000) (100 . "AcDbLine") (10 1532.8578888398 -41.4217121280 0.0000000000) (11 1532.8578888398 -51.4217121280 0.0000000000) (210 0.0000000000 0.0000000000 1.0000000000))
((0 . "LINE") (100 . "AcDbEntity") (67 . 0) (8 . "A-Window") (62 . 252) (420 . 9868950) (6 . "Continuous") (100 . "AcDbLine") (10 1533.2328888398 -47.3049731404 0.0000000000) (11 1533.2328888398 -49.3380171897 0.0000000000) (210 0.0000000000 0.0000000000 1.0000000000))
((0 . "LINE") (100 . "AcDbEntity") (67 . 0) (8 . "A-Window") (62 . 252) (420 . 9868950) (6 . "Continuous") (100 . "AcDbLine") (10 1529.9415837781 -46.0467121280 0.0000000000) (11 1529.9415837781 -46.7967121280 0.0000000000) (210 0.0000000000 0.0000000000 1.0000000000))
((0 . "ARC") (100 . "AcDbEntity") (67 . 0) (8 . "A-Window") (62 . 252) (420 . 9868950) (6 . "Continuous") (100 . "AcDbCircle") (10 -1531.9560383097 -45.5172243919 0.0000000000) (40 . 0.5295876191) (210 0.0000000000 0.0000000000 -1.0000000000) (100 . "AcDbArc") (50 . 3.0398793474) (51 . -1.5902185321))
((0 . "LINE") (100 . "AcDbEntity") (67 . 0) (8 . "A-Window") (62 . 252) (420 . 9868950) (6 . "Continuous") (100 . "AcDbLine") (10 1529.9415837781 -46.0467121280 0.0000000000) (11 1531.9663234225 -46.0467121280 0.0000000000) (210 0.0000000000 0.0000000000 1.0000000000))
((0 . "ARC") (100 . "AcDbEntity") (67 . 0) (8 . "A-Window") (62 . 252) (420 . 9868950) (6 . "Continuous") (100 . "AcDbCircle") (10 -1532.0150038678 -47.2638695594 0.0000000000) (40 . 0.4696869718) (210 0.0000000000 0.0000000000 -1.0000000000) (100 . "AcDbArc") (50 . 1.4669654186) (51 . -3.0539678520))
((0 . "LINE") (100 . "AcDbEntity") (67 . 0) (8 . "A-Window") (62 . 252) (420 . 9868950) (6 . "Continuous") (100 . "AcDbLine") (10 1529.9415837781 -46.7967121280 0.0000000000) (11 1531.9663234225 -46.7967121280 0.0000000000) (210 0.0000000000 0.0000000000 1.0000000000))
((0 . "LINE") (100 . "AcDbEntity") (67 . 0) (8 . "A-Window") (62 . 252) (420 . 9868950) (6 . "Continuous") (100 . "AcDbLine") (10 1532.4828888398 -47.3049731404 0.0000000000) (11 1532.4828888398 -49.3380171897 0.0000000000) (210 0.0000000000 0.0000000000 1.0000000000))
((0 . "LINE") (100 . "AcDbEntity") (67 . 0) (8 . "A-Window") (62 . 252) (420 . 9868950) (6 . "Continuous") (100 . "AcDbLine") (10 1532.4828888398 -49.3380171897 0.0000000000) (11 1533.2328888398 -49.3380171897 0.0000000000) (210 0.0000000000 0.0000000000 1.0000000000))
((0 . "LINE") (100 . "AcDbEntity") (67 . 0) (8 . "A-Window") (62 . 252) (420 . 9868950) (6 . "Continuous") (100 . "AcDbLine") (10 1532.4828888398 -43.5054070663 0.0000000000) (11 1533.2328888398 -43.5054070663 0.0000000000) (210 0.0000000000 0.0000000000 1.0000000000))
((0 . "LINE") (100 . "AcDbEntity") (67 . 0) (8 . "A-Window") (62 . 252) (420 . 9868950) (6 . "Continuous") (100 . "AcDbLine") (10 1533.2328888398 -43.5054070663 0.0000000000) (11 1533.2328888398 -45.4634511157 0.0000000000) (210 0.0000000000 0.0000000000 1.0000000000))
((0 . "LINE") (100 . "AcDbEntity") (67 . 0) (8 . "A-Window") (62 . 252) (420 . 9868950) (6 . "Continuous") (100 . "AcDbLine") (10 1532.4828888398 -43.5054070663 0.0000000000) (11 1532.4828888398 -45.4634511157 0.0000000000) (210 0.0000000000 0.0000000000 1.0000000000))
((0 . "LINE") (100 . "AcDbEntity") (67 . 0) (8 . "A-Window") (62 . 252) (420 . 9868950) (6 . "Continuous") (100 . "AcDbLine") (10 1535.7741939015 -46.0467121280 0.0000000000) (11 1535.7741939015 -46.7967121280 0.0000000000) (210 0.0000000000 0.0000000000 1.0000000000))
((0 . "LINE") (100 . "AcDbEntity") (67 . 0) (8 . "A-Window") (62 . 252) (420 . 9868950) (6 . "Continuous") (100 . "AcDbLine") (10 1533.8161498521 -46.0467121280 0.0000000000) (11 1535.7741939015 -46.0467121280 0.0000000000) (210 0.0000000000 0.0000000000 1.0000000000))
((0 . "LINE") (100 . "AcDbEntity") (67 . 0) (8 . "A-Window") (62 . 252) (420 . 9868950) (6 . "Continuous") (100 . "AcDbLine") (10 1533.8161498521 -46.7967121280 0.0000000000) (11 1535.7741939015 -46.7967121280 0.0000000000) (210 0.0000000000 0.0000000000 1.0000000000))
((0 . "LINE") (100 . "AcDbEntity") (67 . 0) (8 . "A-Window") (62 . 8) (6 . "CENTER") (48 . 0.5000000000) (100 . "AcDbLine") (10 1527.8578888398 45.5782878720 0.0000000000) (11 1537.8578888398 45.5782878720 0.0000000000) (210 0.0000000000 0.0000000000 1.0000000000))
((0 . "ARC") (100 . "AcDbEntity") (67 . 0) (8 . "A-Window") (62 . 252) (420 . 9868950) (6 . "Continuous") (100 . "AcDbCircle") (10 1533.8161498521 44.6200268596 0.0000000000) (40 . 0.5832610123) (210 0.0000000000 0.0000000000 1.0000000000) (100 . "AcDbArc") (50 . 1.5707963268) (51 . 3.1415926536))
((0 . "ARC") (100 . "AcDbEntity") (67 . 0) (8 . "A-Window") (62 . 252) (420 . 9868950) (6 . "Continuous") (100 . "AcDbCircle") (10 1533.7561196317 46.4731940600 0.0000000000) (40 . 0.5233603650) (210 0.0000000000 0.0000000000 1.0000000000) (100 . "AcDbArc") (50 . -3.1193400384) (51 . -1.4558418125))
((0 . "CIRCLE") (100 . "AcDbEntity") (67 . 0) (8 . "A-Window") (62 . 252) (420 . 9868950) (6 . "Continuous") (100 . "AcDbCircle") (10 1532.8578888398 45.5782878720 0.0000000000) (40 . 4.0000000000) (210 0.0000000000 0.0000000000 1.0000000000))
((0 . "LINE") (100 . "AcDbEntity") (67 . 0) (8 . "A-Window") (62 . 8) (6 . "CENTER") (48 . 0.5000000000) (100 . "AcDbLine") (10 1532.8578888398 40.5782878720 0.0000000000) (11 1532.8578888398 50.5782878720 0.0000000000) (210 0.0000000000 0.0000000000 1.0000000000))
((0 . "LINE") (100 . "AcDbEntity") (67 . 0) (8 . "A-Window") (62 . 252) (420 . 9868950) (6 . "Continuous") (100 . "AcDbLine") (10 1533.2328888398 46.4615488843 0.0000000000) (11 1533.2328888398 48.4945929337 0.0000000000) (210 0.0000000000 0.0000000000 1.0000000000))
((0 . "LINE") (100 . "AcDbEntity") (67 . 0) (8 . "A-Window") (62 . 252) (420 . 9868950) (6 . "Continuous") (100 . "AcDbLine") (10 1529.9415837781 45.2032878720 0.0000000000) (11 1529.9415837781 45.9532878720 0.0000000000) (210 0.0000000000 0.0000000000 1.0000000000))
((0 . "ARC") (100 . "AcDbEntity") (67 . 0) (8 . "A-Window") (62 . 252) (420 . 9868950) (6 . "Continuous") (100 . "AcDbCircle") (10 1531.9560383097 44.6738001358 0.0000000000) (40 . 0.5295876191) (210 0.0000000000 0.0000000000 1.0000000000) (100 . "AcDbArc") (50 . -0.1017133062) (51 . 1.5513741215))
((0 . "LINE") (100 . "AcDbEntity") (67 . 0) (8 . "A-Window") (62 . 252) (420 . 9868950) (6 . "Continuous") (100 . "AcDbLine") (10 1529.9415837781 45.2032878720 0.0000000000) (11 1531.9663234225 45.2032878720 0.0000000000) (210 0.0000000000 0.0000000000 1.0000000000))
((0 . "ARC") (100 . "AcDbEntity") (67 . 0) (8 . "A-Window") (62 . 252) (420 . 9868950) (6 . "Continuous") (100 . "AcDbCircle") (10 1532.0150038678 46.4204453034 0.0000000000) (40 . 0.4696869718) (210 0.0000000000 0.0000000000 1.0000000000) (100 . "AcDbArc") (50 . -1.6746272350) (51 . 0.0876248016))
((0 . "LINE") (100 . "AcDbEntity") (67 . 0) (8 . "A-Window") (62 . 252) (420 . 9868950) (6 . "Continuous") (100 . "AcDbLine") (10 1529.9415837781 45.9532878720 0.0000000000) (11 1531.9663234225 45.9532878720 0.0000000000) (210 0.0000000000 0.0000000000 1.0000000000))
((0 . "LINE") (100 . "AcDbEntity") (67 . 0) (8 . "A-Window") (62 . 252) (420 . 9868950) (6 . "Continuous") (100 . "AcDbLine") (10 1532.4828888398 46.4615488843 0.0000000000) (11 1532.4828888398 48.4945929337 0.0000000000) (210 0.0000000000 0.0000000000 1.0000000000))
((0 . "LINE") (100 . "AcDbEntity") (67 . 0) (8 . "A-Window") (62 . 252) (420 . 9868950) (6 . "Continuous") (100 . "AcDbLine") (10 1532.4828888398 48.4945929337 0.0000000000) (11 1533.2328888398 48.4945929337 0.0000000000) (210 0.0000000000 0.0000000000 1.0000000000))
((0 . "LINE") (100 . "AcDbEntity") (67 . 0) (8 . "A-Window") (62 . 252) (420 . 9868950) (6 . "Continuous") (100 . "AcDbLine") (10 1532.4828888398 42.6619828103 0.0000000000) (11 1533.2328888398 42.6619828103 0.0000000000) (210 0.0000000000 0.0000000000 1.0000000000))
((0 . "LINE") (100 . "AcDbEntity") (67 . 0) (8 . "A-Window") (62 . 252) (420 . 9868950) (6 . "Continuous") (100 . "AcDbLine") (10 1533.2328888398 42.6619828103 0.0000000000) (11 1533.2328888398 44.6200268596 0.0000000000) (210 0.0000000000 0.0000000000 1.0000000000))
((0 . "LINE") (100 . "AcDbEntity") (67 . 0) (8 . "A-Window") (62 . 252) (420 . 9868950) (6 . "Continuous") (100 . "AcDbLine") (10 1532.4828888398 42.6619828103 0.0000000000) (11 1532.4828888398 44.6200268596 0.0000000000) (210 0.0000000000 0.0000000000 1.0000000000))
((0 . "LINE") (100 . "AcDbEntity") (67 . 0) (8 . "A-Window") (62 . 252) (420 . 9868950) (6 . "Continuous") (100 . "AcDbLine") (10 1535.7741939015 45.2032878720 0.0000000000) (11 1535.7741939015 45.9532878720 0.0000000000) (210 0.0000000000 0.0000000000 1.0000000000))
((0 . "LINE") (100 . "AcDbEntity") (67 . 0) (8 . "A-Window") (62 . 252) (420 . 9868950) (6 . "Continuous") (100 . "AcDbLine") (10 1533.8161498521 45.2032878720 0.0000000000) (11 1535.7741939015 45.2032878720 0.0000000000) (210 0.0000000000 0.0000000000 1.0000000000))
((0 . "LINE") (100 . "AcDbEntity") (67 . 0) (8 . "A-Window") (62 . 252) (420 . 9868950) (6 . "Continuous") (100 . "AcDbLine") (10 1533.8161498521 45.9532878720 0.0000000000) (11 1535.7741939015 45.9532878720 0.0000000000) (210 0.0000000000 0.0000000000 1.0000000000))
((0 . "LWPOLYLINE") (100 . "AcDbEntity") (67 . 0) (8 . "A-Window") (62 . 252) (420 . 9868950) (6 . "Continuous") (100 . "AcDbPolyline") (90 . 4) (70 . 1) (43 . 0.0000000000) (38 . 0.0000000000) (39 . 0.0000000000) (10 1632.8578888398 -15.9217121281) (40 . 0.0000000000) (41 . 0.0000000000) (42 . 0.0000000000) (91 . 0) (10 1470.8578888398 -15.9217121281) (40 . 0.0000000000) (41 . 0.0000000000) (42 . 0.0000000000) (91 . 0) (10 1470.8578888398 -8.9217121281) (40 . 0.0000000000) (41 . 0.0000000000) (42 . 0.0000000000) (91 . 0) (10 1632.8578888398 -8.9217121281) (40 . 0.0000000000) (41 . 0.0000000000) (42 . 0.0000000000) (91 . 0) (210 0.0000000000 0.0000000000 1.0000000000))
((0 . "LWPOLYLINE") (100 . "AcDbEntity") (67 . 0) (8 . "A-Window") (62 . 252) (420 . 9868950) (6 . "Continuous") (100 . "AcDbPolyline") (90 . 4) (70 . 1) (43 . 0.0000000000) (38 . 0.0000000000) (39 . 0.0000000000) (10 1632.8578888398 15.0782878721) (40 . 0.0000000000) (41 . 0.0000000000) (42 . 0.0000000000) (91 . 0) (10 1470.8578888398 15.0782878721) (40 . 0.0000000000) (41 . 0.0000000000) (42 . 0.0000000000) (91 . 0) (10 1470.8578888398 8.0782878721) (40 . 0.0000000000) (41 . 0.0000000000) (42 . 0.0000000000) (91 . 0) (10 1632.8578888398 8.0782878721) (40 . 0.0000000000) (41 . 0.0000000000) (42 . 0.0000000000) (91 . 0) (210 0.0000000000 0.0000000000 1.0000000000))
((0 . "CIRCLE") (100 . "AcDbEntity") (67 . 0) (8 . "A-Window") (62 . 252) (420 . 9868950) (6 . "Continuous") (100 . "AcDbCircle") (10 1589.8578888398 -2.6287009723 0.0000000000) (40 . 10.1131438220) (210 0.0000000000 0.0000000000 1.0000000000))
((0 . "CIRCLE") (100 . "AcDbEntity") (67 . 0) (8 . "A-Window") (62 . 252) (420 . 9868950) (6 . "Continuous") (100 . "AcDbCircle") (10 1589.8578888398 -2.6287009723 0.0000000000) (40 . 9.1131438220) (210 0.0000000000 0.0000000000 1.0000000000))
((0 . "LINE") (100 . "AcDbEntity") (67 . 0) (8 . "A-Window") (62 . 252) (420 . 9868950) (6 . "CENTER") (48 . 100.0000000000) (100 . "AcDbLine") (10 1609.1538820688 -2.6287009723 0.0000000000) (11 1570.5618956107 -2.6287009723 0.0000000000) (210 0.0000000000 0.0000000000 1.0000000000))
((0 . "LINE") (100 . "AcDbEntity") (67 . 0) (8 . "A-Window") (62 . 252) (420 . 9868950) (6 . "CENTER") (48 . 100.0000000000) (100 . "AcDbLine") (10 1589.8578888398 -21.9246942014 0.0000000000) (11 1589.8578888398 19.6672922568 0.0000000000) (210 0.0000000000 0.0000000000 1.0000000000))
((0 . "LINE") (100 . "AcDbEntity") (67 . 0) (8 . "A-Window") (62 . 252) (420 . 9868950) (6 . "Continuous") (100 . "AcDbLine") (10 1632.8578888398 6.8265860749 0.0000000000) (11 1632.8578888398 -1.9217121280 0.0000000000) (210 0.0000000000 0.0000000000 1.0000000000))
((0 . "LINE") (100 . "AcDbEntity") (67 . 0) (8 . "A-Window") (62 . 148) (6 . "Continuous") (100 . "AcDbLine") (10 935.0144882150 -10.9920844850 0.0000000000) (11 935.0144882150 -46.1720844849 0.0000000000) (210 0.0000000000 0.0000000000 1.0000000000))
((0 . "CIRCLE") (100 . "AcDbEntity") (67 . 0) (8 . "A-Window") (62 . 148) (6 . "Continuous") (100 . "AcDbCircle") (10 920.1707382150 -65.1720844847 0.0000000000) (40 . 19.0000000000) (210 0.0000000000 0.0000000000 1.0000000000))
((0 . "LINE") (100 . "AcDbEntity") (67 . 0) (8 . "A-Window") (62 . 148) (6 . "Continuous") (100 . "AcDbLine") (10 935.0144882150 -10.9920844850 0.0000000000) (11 935.0144882150 -53.3119375233 0.0000000000) (210 0.0000000000 0.0000000000 1.0000000000))
((0 . "LINE") (100 . "AcDbEntity") (67 . 0) (8 . "A-Window") (62 . 148) (6 . "Continuous") (100 . "AcDbLine") (10 905.3269882150 -10.9920844850 0.0000000000) (11 905.3269882150 -53.3119375233 0.0000000000) (210 0.0000000000 0.0000000000 1.0000000000))
((0 . "LWPOLYLINE") (100 . "AcDbEntity") (67 . 0) (8 . "A-Window") (62 . 148) (6 . "Continuous") (100 . "AcDbPolyline") (90 . 5) (70 . 0) (43 . 0.0000000000) (38 . 0.0000000000) (39 . 0.0000000000) (10 897.3427648703 -5.6720844846) (40 . 0.0000000000) (41 . 0.0000000000) (42 . 0.0000000000) (91 . 0) (10 942.9987115594 -5.6720844848) (40 . 0.0000000000) (41 . 0.0000000000) (42 . -0.2220002644) (91 . 0) (10 940.9533959965 -7.1920844849) (40 . 0.0000000000) (41 . 0.0000000000) (42 . 0.0000000000) (91 . 0) (10 899.3880804336 -7.1920844849) (40 . 0.0000000000) (41 . 0.0000000000) (42 . -0.2220002644) (91 . 0) (10 897.3427648703 -5.6720844846) (40 . 0.0000000000) (41 . 0.0000000000) (42 . 6.7869977914) (91 . 0) (210 0.0000000000 0.0000000000 1.0000000000))
((0 . "LWPOLYLINE") (100 . "AcDbEntity") (67 . 0) (8 . "A-Window") (62 . 148) (6 . "Continuous") (100 . "AcDbPolyline") (90 . 4) (70 . 0) (43 . 0.0000000000) (38 . 0.0000000000) (39 . 0.0000000000) (10 940.9533959965 -7.1920844849) (40 . 0.0000000000) (41 . 0.0000000000) (42 . -0.2225651805) (91 . 0) (10 938.9080804337 -10.9920844850) (40 . 0.0000000000) (41 . 0.0000000000) (42 . 0.0000000000) (91 . 0) (10 901.4333959965 -10.9920844850) (40 . 0.0000000000) (41 . 0.0000000000) (42 . -0.2225651805) (91 . 0) (10 899.3880804336 -7.1920844849) (40 . 0.0000000000) (41 . 0.0000000000) (42 . 1.8579040169) (91 . 0) (210 0.0000000000 0.0000000000 1.0000000000))
((0 . "LINE") (100 . "AcDbEntity") (67 . 0) (8 . "A-Window") (62 . 148) (6 . "Continuous") (100 . "AcDbLine") (10 935.0144882150 11.6479155154 0.0000000000) (11 935.0144882150 48.3279155153 0.0000000000) (210 0.0000000000 0.0000000000 1.0000000000))
((0 . "CIRCLE") (100 . "AcDbEntity") (67 . 0) (8 . "A-Window") (62 . 148) (6 . "Continuous") (100 . "AcDbCircle") (10 920.1707382150 67.3279155153 0.0000000000) (40 . 19.0000000000) (210 0.0000000000 0.0000000000 1.0000000000))
((0 . "LINE") (100 . "AcDbEntity") (67 . 0) (8 . "A-Window") (62 . 148) (6 . "Continuous") (100 . "AcDbLine") (10 935.0144882150 11.6479155154 0.0000000000) (11 935.0144882150 55.4677685538 0.0000000000) (210 0.0000000000 0.0000000000 1.0000000000))
((0 . "LINE") (100 . "AcDbEntity") (67 . 0) (8 . "A-Window") (62 . 148) (6 . "Continuous") (100 . "AcDbLine") (10 905.3269882150 11.6479155154 0.0000000000) (11 905.3269882150 55.4677685538 0.0000000000) (210 0.0000000000 0.0000000000 1.0000000000))
((0 . "LWPOLYLINE") (100 . "AcDbEntity") (67 . 0) (8 . "A-Window") (62 . 148) (6 . "Continuous") (100 . "AcDbPolyline") (90 . 5) (70 . 0) (43 . 0.0000000000) (38 . 0.0000000000) (39 . 0.0000000000) (10 897.3427648703 6.3279155151) (40 . 0.0000000000) (41 . 0.0000000000) (42 . 0.0000000000) (91 . 0) (10 942.9987115594 6.3279155154) (40 . 0.0000000000) (41 . 0.0000000000) (42 . 0.2220002644) (91 . 0) (10 940.9533959965 7.8479155154) (40 . 0.0000000000) (41 . 0.0000000000) (42 . 0.0000000000) (91 . 0) (10 899.3880804336 7.8479155154) (40 . 0.0000000000) (41 . 0.0000000000) (42 . 0.2220002644) (91 . 0) (10 897.3427648703 6.3279155151) (40 . 0.0000000000) (41 . 0.0000000000) (42 . -6.7869977914) (91 . 0) (210 0.0000000000 0.0000000000 1.0000000000))
((0 . "LWPOLYLINE") (100 . "AcDbEntity") (67 . 0) (8 . "A-Window") (62 . 148) (6 . "Continuous") (100 . "AcDbPolyline") (90 . 4) (70 . 0) (43 . 0.0000000000) (38 . 0.0000000000) (39 . 0.0000000000) (10 940.9533959965 7.8479155154) (40 . 0.0000000000) (41 . 0.0000000000) (42 . 0.2225651805) (91 . 0) (10 938.9080804337 11.6479155154) (40 . 0.0000000000) (41 . 0.0000000000) (42 . 0.0000000000) (91 . 0) (10 901.4333959965 11.6479155154) (40 . 0.0000000000) (41 . 0.0000000000) (42 . 0.2225651805) (91 . 0) (10 899.3880804336 7.8479155154) (40 . 0.0000000000) (41 . 0.0000000000) (42 . -1.8579040169) (91 . 0) (210 0.0000000000 0.0000000000 1.0000000000))
((0 . "LINE") (100 . "AcDbEntity") (67 . 0) (8 . "A-Window") (62 . 8) (6 . "HIDDEN") (48 . 200.0000000000) (100 . "AcDbLine") (10 32.8578888398 0.7496276428 0.0000000000) (11 667.3070072813 334.6450221887 0.0000000000) (210 0.0000000000 0.0000000000 1.0000000000))
((0 . "ARC") (100 . "AcDbEntity") (67 . 0) (8 . "A-Window") (62 . 8) (6 . "HIDDEN") (48 . 200.0000000000) (100 . "AcDbCircle") (10 -452.2351071949 23.9172815797 0.0000000000) (40 . 377.8989957167) (210 0.0000000000 0.0000000000 -1.0000000000) (100 . "AcDbArc") (50 . 2.1762380686) (51 . -2.1762380686))
((0 . "LWPOLYLINE") (100 . "AcDbEntity") (67 . 0) (8 . "A-Window") (62 . 252) (420 . 9868950) (6 . "Continuous") (100 . "AcDbPolyline") (90 . 8) (70 . 1) (43 . 0.0000000000) (38 . 0.0000000000) (39 . 0.0000000000) (10 -32.7530489914 4.9999999995) (40 . 0.0000000000) (41 . 0.0000000000) (42 . 0.0000000000) (91 . 0) (10 -32.7530489914 -4.9999999996) (40 . 0.0000000000) (41 . 0.0000000000) (42 . 0.0000000000) (91 . 0) (10 -33.7530489914 -5.9999999996) (40 . 0.0000000000) (41 . 0.0000000000) (42 . 0.0000000000) (91 . 0) (10 -828.8578888404 -5.6720844848) (40 . 0.0000000000) (41 . 0.0000000000) (42 . 0.0000000000) (91 . 0) (10 -829.8578888404 -4.6720844848) (40 . 0.0000000000) (41 . 0.0000000000) (42 . 0.0000000000) (91 . 0) (10 -829.8578888404 5.3279155143) (40 . 0.0000000000) (41 . 0.0000000000) (42 . 0.0000000000) (91 . 0) (10 -828.8578888404 6.3279155143) (40 . 0.0000000000) (41 . 0.0000000000) (42 . 0.0000000000) (91 . 0) (10 -33.7530489914 5.9999999995) (40 . 0.0000000000) (41 . 0.0000000000) (42 . 0.0000000000) (91 . 0) (210 0.0000000000 0.0000000000 -1.0000000000))
((0 . "LINE") (100 . "AcDbEntity") (67 . 0) (8 . "A-Window") (62 . 8) (6 . "HIDDEN") (48 . 200.0000000000) (100 . "AcDbLine") (10 32.8578888398 -0.7496276419 0.0000000000) (11 667.3070072813 -286.8104590285 0.0000000000) (210 0.0000000000 0.0000000000 1.0000000000))
((0 . "LINE") (100 . "AcDbEntity") (67 . 0) (8 . "A-Window") (62 . 2) (6 . "Continuous") (100 . "AcDbLine") (10 114.3578888426 -7.9217121282 0.0000000000) (11 32.8578888426 -7.9217121282 0.0000000000) (210 0.0000000000 0.0000000000 1.0000000000))
((0 . "LINE") (100 . "AcDbEntity") (67 . 0) (8 . "A-Window") (62 . 8) (6 . "CENTER") (48 . 0.5000000000) (100 . "AcDbLine") (10 289.8578888413 -46.4217121280 0.0000000000) (11 299.8578888413 -46.4217121280 0.0000000000) (210 0.0000000000 0.0000000000 1.0000000000))
((0 . "ARC") (100 . "AcDbEntity") (67 . 0) (8 . "A-Window") (62 . 252) (420 . 9868950) (6 . "Continuous") (100 . "AcDbCircle") (10 -295.8161498537 -45.4634511157 0.0000000000) (40 . 0.5832610123) (210 0.0000000000 0.0000000000 -1.0000000000) (100 . "AcDbArc") (50 . -1.5707963268) (51 . 0.0000000000))
((0 . "ARC") (100 . "AcDbEntity") (67 . 0) (8 . "A-Window") (62 . 252) (420 . 9868950) (6 . "Continuous") (100 . "AcDbCircle") (10 -295.7561196332 -47.3166183160 0.0000000000) (40 . 0.5233603650) (210 0.0000000000 0.0000000000 -1.0000000000) (100 . "AcDbArc") (50 . 0.0222526151) (51 . 1.6857508410))
((0 . "CIRCLE") (100 . "AcDbEntity") (67 . 0) (8 . "A-Window") (62 . 252) (420 . 9868950) (6 . "Continuous") (100 . "AcDbCircle") (10 -294.8578888413 -46.4217121280 0.0000000000) (40 . 4.0000000000) (210 0.0000000000 0.0000000000 -1.0000000000))
((0 . "LINE") (100 . "AcDbEntity") (67 . 0) (8 . "A-Window") (62 . 8) (6 . "CENTER") (48 . 0.5000000000) (100 . "AcDbLine") (10 294.8578888413 -41.4217121280 0.0000000000) (11 294.8578888413 -51.4217121280 0.0000000000) (210 0.0000000000 0.0000000000 1.0000000000))
((0 . "LINE") (100 . "AcDbEntity") (67 . 0) (8 . "A-Window") (62 . 252) (420 . 9868950) (6 . "Continuous") (100 . "AcDbLine") (10 295.2328888413 -47.3049731404 0.0000000000) (11 295.2328888413 -49.3380171897 0.0000000000) (210 0.0000000000 0.0000000000 1.0000000000))
((0 . "LINE") (100 . "AcDbEntity") (67 . 0) (8 . "A-Window") (62 . 252) (420 . 9868950) (6 . "Continuous") (100 . "AcDbLine") (10 291.9415837796 -46.0467121280 0.0000000000) (11 291.9415837796 -46.7967121280 0.0000000000) (210 0.0000000000 0.0000000000 1.0000000000))
((0 . "ARC") (100 . "AcDbEntity") (67 . 0) (8 . "A-Window") (62 . 252) (420 . 9868950) (6 . "Continuous") (100 . "AcDbCircle") (10 -293.9560383112 -45.5172243919 0.0000000000) (40 . 0.5295876191) (210 0.0000000000 0.0000000000 -1.0000000000) (100 . "AcDbArc") (50 . 3.0398793474) (51 . -1.5902185321))
((0 . "LINE") (100 . "AcDbEntity") (67 . 0) (8 . "A-Window") (62 . 252) (420 . 9868950) (6 . "Continuous") (100 . "AcDbLine") (10 291.9415837796 -46.0467121280 0.0000000000) (11 293.9663234241 -46.0467121280 0.0000000000) (210 0.0000000000 0.0000000000 1.0000000000))
((0 . "ARC") (100 . "AcDbEntity") (67 . 0) (8 . "A-Window") (62 . 252) (420 . 9868950) (6 . "Continuous") (100 . "AcDbCircle") (10 -294.0150038693 -47.2638695594 0.0000000000) (40 . 0.4696869718) (210 0.0000000000 0.0000000000 -1.0000000000) (100 . "AcDbArc") (50 . 1.4669654186) (51 . -3.0539678520))
((0 . "LINE") (100 . "AcDbEntity") (67 . 0) (8 . "A-Window") (62 . 252) (420 . 9868950) (6 . "Continuous") (100 . "AcDbLine") (10 291.9415837796 -46.7967121280 0.0000000000) (11 293.9663234241 -46.7967121280 0.0000000000) (210 0.0000000000 0.0000000000 1.0000000000))
((0 . "LINE") (100 . "AcDbEntity") (67 . 0) (8 . "A-Window") (62 . 252) (420 . 9868950) (6 . "Continuous") (100 . "AcDbLine") (10 294.4828888413 -47.3049731404 0.0000000000) (11 294.4828888413 -49.3380171897 0.0000000000) (210 0.0000000000 0.0000000000 1.0000000000))
((0 . "LINE") (100 . "AcDbEntity") (67 . 0) (8 . "A-Window") (62 . 252) (420 . 9868950) (6 . "Continuous") (100 . "AcDbLine") (10 294.4828888413 -49.3380171897 0.0000000000) (11 295.2328888413 -49.3380171897 0.0000000000) (210 0.0000000000 0.0000000000 1.0000000000))
((0 . "LINE") (100 . "AcDbEntity") (67 . 0) (8 . "A-Window") (62 . 252) (420 . 9868950) (6 . "Continuous") (100 . "AcDbLine") (10 294.4828888413 -43.5054070663 0.0000000000) (11 295.2328888413 -43.5054070663 0.0000000000) (210 0.0000000000 0.0000000000 1.0000000000))
((0 . "LINE") (100 . "AcDbEntity") (67 . 0) (8 . "A-Window") (62 . 252) (420 . 9868950) (6 . "Continuous") (100 . "AcDbLine") (10 295.2328888413 -43.5054070663 0.0000000000) (11 295.2328888413 -45.4634511157 0.0000000000) (210 0.0000000000 0.0000000000 1.0000000000))
((0 . "LINE") (100 . "AcDbEntity") (67 . 0) (8 . "A-Window") (62 . 252) (420 . 9868950) (6 . "Continuous") (100 . "AcDbLine") (10 294.4828888413 -43.5054070663 0.0000000000) (11 294.4828888413 -45.4634511157 0.0000000000) (210 0.0000000000 0.0000000000 1.0000000000))
((0 . "LINE") (100 . "AcDbEntity") (67 . 0) (8 . "A-Window") (62 . 252) (420 . 9868950) (6 . "Continuous") (100 . "AcDbLine") (10 297.7741939030 -46.0467121280 0.0000000000) (11 297.7741939030 -46.7967121280 0.0000000000) (210 0.0000000000 0.0000000000 1.0000000000))
((0 . "LINE") (100 . "AcDbEntity") (67 . 0) (8 . "A-Window") (62 . 252) (420 . 9868950) (6 . "Continuous") (100 . "AcDbLine") (10 295.8161498537 -46.0467121280 0.0000000000) (11 297.7741939030 -46.0467121280 0.0000000000) (210 0.0000000000 0.0000000000 1.0000000000))
((0 . "LINE") (100 . "AcDbEntity") (67 . 0) (8 . "A-Window") (62 . 252) (420 . 9868950) (6 . "Continuous") (100 . "AcDbLine") (10 295.8161498537 -46.7967121280 0.0000000000) (11 297.7741939030 -46.7967121280 0.0000000000) (210 0.0000000000 0.0000000000 1.0000000000))
((0 . "LWPOLYLINE") (100 . "AcDbEntity") (67 . 0) (8 . "A-Window") (62 . 252) (420 . 9868950) (6 . "Continuous") (100 . "AcDbPolyline") (90 . 4) (70 . 1) (43 . 0.0000000000) (38 . 0.0000000000) (39 . 0.0000000000) (10 -32.8578888398 -61.4217121280) (40 . 0.0000000000) (41 . 0.0000000000) (42 . 0.0000000000) (91 . 0) (10 -324.8578888413 -61.4217121280) (40 . 0.0000000000) (41 . 0.0000000000) (42 . 0.0000000000) (91 . 0) (10 -324.8578888413 60.5782878720) (40 . 0.0000000000) (41 . 0.0000000000) (42 . 0.0000000000) (91 . 0) (10 -32.8578888398 60.5782878720) (40 . 0.0000000000) (41 . 0.0000000000) (42 . 0.0000000000) (91 . 0) (210 0.0000000000 0.0000000000 -1.0000000000))
((0 . "LINE") (100 . "AcDbEntity") (67 . 0) (8 . "A-Window") (62 . 8) (6 . "CENTER") (48 . 0.5000000000) (100 . "AcDbLine") (10 289.8578888413 45.5782878720 0.0000000000) (11 299.8578888413 45.5782878720 0.0000000000) (210 0.0000000000 0.0000000000 1.0000000000))
((0 . "ARC") (100 . "AcDbEntity") (67 . 0) (8 . "A-Window") (62 . 252) (420 . 9868950) (6 . "Continuous") (100 . "AcDbCircle") (10 295.8161498537 44.6200268596 0.0000000000) (40 . 0.5832610123) (210 0.0000000000 0.0000000000 1.0000000000) (100 . "AcDbArc") (50 . 1.5707963268) (51 . 3.1415926536))
((0 . "ARC") (100 . "AcDbEntity") (67 . 0) (8 . "A-Window") (62 . 252) (420 . 9868950) (6 . "Continuous") (100 . "AcDbCircle") (10 295.7561196332 46.4731940600 0.0000000000) (40 . 0.5233603650) (210 0.0000000000 0.0000000000 1.0000000000) (100 . "AcDbArc") (50 . -3.1193400384) (51 . -1.4558418125))
((0 . "CIRCLE") (100 . "AcDbEntity") (67 . 0) (8 . "A-Window") (62 . 252) (420 . 9868950) (6 . "Continuous") (100 . "AcDbCircle") (10 294.8578888413 45.5782878720 0.0000000000) (40 . 4.0000000000) (210 0.0000000000 0.0000000000 1.0000000000))
((0 . "LINE") (100 . "AcDbEntity") (67 . 0) (8 . "A-Window") (62 . 8) (6 . "CENTER") (48 . 0.5000000000) (100 . "AcDbLine") (10 294.8578888413 40.5782878720 0.0000000000) (11 294.8578888413 50.5782878720 0.0000000000) (210 0.0000000000 0.0000000000 1.0000000000))
((0 . "LINE") (100 . "AcDbEntity") (67 . 0) (8 . "A-Window") (62 . 252) (420 . 9868950) (6 . "Continuous") (100 . "AcDbLine") (10 295.2328888413 46.4615488843 0.0000000000) (11 295.2328888413 48.4945929337 0.0000000000) (210 0.0000000000 0.0000000000 1.0000000000))
((0 . "LINE") (100 . "AcDbEntity") (67 . 0) (8 . "A-Window") (62 . 252) (420 . 9868950) (6 . "Continuous") (100 . "AcDbLine") (10 291.9415837796 45.2032878720 0.0000000000) (11 291.9415837796 45.9532878720 0.0000000000) (210 0.0000000000 0.0000000000 1.0000000000))
((0 . "ARC") (100 . "AcDbEntity") (67 . 0) (8 . "A-Window") (62 . 252) (420 . 9868950) (6 . "Continuous") (100 . "AcDbCircle") (10 293.9560383112 44.6738001358 0.0000000000) (40 . 0.5295876191) (210 0.0000000000 0.0000000000 1.0000000000) (100 . "AcDbArc") (50 . -0.1017133062) (51 . 1.5513741215))
((0 . "LINE") (100 . "AcDbEntity") (67 . 0) (8 . "A-Window") (62 . 252) (420 . 9868950) (6 . "Continuous") (100 . "AcDbLine") (10 291.9415837796 45.2032878720 0.0000000000) (11 293.9663234241 45.2032878720 0.0000000000) (210 0.0000000000 0.0000000000 1.0000000000))
((0 . "ARC") (100 . "AcDbEntity") (67 . 0) (8 . "A-Window") (62 . 252) (420 . 9868950) (6 . "Continuous") (100 . "AcDbCircle") (10 294.0150038693 46.4204453034 0.0000000000) (40 . 0.4696869718) (210 0.0000000000 0.0000000000 1.0000000000) (100 . "AcDbArc") (50 . -1.6746272350) (51 . 0.0876248016))
((0 . "LINE") (100 . "AcDbEntity") (67 . 0) (8 . "A-Window") (62 . 252) (420 . 9868950) (6 . "Continuous") (100 . "AcDbLine") (10 291.9415837796 45.9532878720 0.0000000000) (11 293.9663234241 45.9532878720 0.0000000000) (210 0.0000000000 0.0000000000 1.0000000000))
((0 . "LINE") (100 . "AcDbEntity") (67 . 0) (8 . "A-Window") (62 . 252) (420 . 9868950) (6 . "Continuous") (100 . "AcDbLine") (10 294.4828888413 46.4615488843 0.0000000000) (11 294.4828888413 48.4945929337 0.0000000000) (210 0.0000000000 0.0000000000 1.0000000000))
((0 . "LINE") (100 . "AcDbEntity") (67 . 0) (8 . "A-Window") (62 . 252) (420 . 9868950) (6 . "Continuous") (100 . "AcDbLine") (10 294.4828888413 48.4945929337 0.0000000000) (11 295.2328888413 48.4945929337 0.0000000000) (210 0.0000000000 0.0000000000 1.0000000000))
((0 . "LINE") (100 . "AcDbEntity") (67 . 0) (8 . "A-Window") (62 . 252) (420 . 9868950) (6 . "Continuous") (100 . "AcDbLine") (10 294.4828888413 42.6619828103 0.0000000000) (11 295.2328888413 42.6619828103 0.0000000000) (210 0.0000000000 0.0000000000 1.0000000000))
((0 . "LINE") (100 . "AcDbEntity") (67 . 0) (8 . "A-Window") (62 . 252) (420 . 9868950) (6 . "Continuous") (100 . "AcDbLine") (10 295.2328888413 42.6619828103 0.0000000000) (11 295.2328888413 44.6200268596 0.0000000000) (210 0.0000000000 0.0000000000 1.0000000000))
((0 . "LINE") (100 . "AcDbEntity") (67 . 0) (8 . "A-Window") (62 . 252) (420 . 9868950) (6 . "Continuous") (100 . "AcDbLine") (10 294.4828888413 42.6619828103 0.0000000000) (11 294.4828888413 44.6200268596 0.0000000000) (210 0.0000000000 0.0000000000 1.0000000000))
((0 . "LINE") (100 . "AcDbEntity") (67 . 0) (8 . "A-Window") (62 . 252) (420 . 9868950) (6 . "Continuous") (100 . "AcDbLine") (10 297.7741939030 45.2032878720 0.0000000000) (11 297.7741939030 45.9532878720 0.0000000000) (210 0.0000000000 0.0000000000 1.0000000000))
((0 . "LINE") (100 . "AcDbEntity") (67 . 0) (8 . "A-Window") (62 . 252) (420 . 9868950) (6 . "Continuous") (100 . "AcDbLine") (10 295.8161498537 45.2032878720 0.0000000000) (11 297.7741939030 45.2032878720 0.0000000000) (210 0.0000000000 0.0000000000 1.0000000000))
((0 . "LINE") (100 . "AcDbEntity") (67 . 0) (8 . "A-Window") (62 . 252) (420 . 9868950) (6 . "Continuous") (100 . "AcDbLine") (10 295.8161498537 45.9532878720 0.0000000000) (11 297.7741939030 45.9532878720 0.0000000000) (210 0.0000000000 0.0000000000 1.0000000000))
((0 . "LINE") (100 . "AcDbEntity") (67 . 0) (8 . "A-Window") (62 . 8) (6 . "CENTER") (48 . 0.5000000000) (100 . "AcDbLine") (10 62.8578888398 -46.4217121280 0.0000000000) (11 52.8578888398 -46.4217121280 0.0000000000) (210 0.0000000000 0.0000000000 1.0000000000))
((0 . "ARC") (100 . "AcDbEntity") (67 . 0) (8 . "A-Window") (62 . 252) (420 . 9868950) (6 . "Continuous") (100 . "AcDbCircle") (10 56.8996278275 -45.4634511157 0.0000000000) (40 . 0.5832610123) (210 0.0000000000 0.0000000000 1.0000000000) (100 . "AcDbArc") (50 . -1.5707963268) (51 . 0.0000000000))
((0 . "ARC") (100 . "AcDbEntity") (67 . 0) (8 . "A-Window") (62 . 252) (420 . 9868950) (6 . "Continuous") (100 . "AcDbCircle") (10 56.9596580479 -47.3166183160 0.0000000000) (40 . 0.5233603650) (210 0.0000000000 0.0000000000 1.0000000000) (100 . "AcDbArc") (50 . 0.0222526151) (51 . 1.6857508410))
((0 . "CIRCLE") (100 . "AcDbEntity") (67 . 0) (8 . "A-Window") (62 . 252) (420 . 9868950) (6 . "Continuous") (100 . "AcDbCircle") (10 57.8578888398 -46.4217121280 0.0000000000) (40 . 4.0000000000) (210 0.0000000000 0.0000000000 1.0000000000))
((0 . "LINE") (100 . "AcDbEntity") (67 . 0) (8 . "A-Window") (62 . 8) (6 . "CENTER") (48 . 0.5000000000) (100 . "AcDbLine") (10 57.8578888398 -41.4217121280 0.0000000000) (11 57.8578888398 -51.4217121280 0.0000000000) (210 0.0000000000 0.0000000000 1.0000000000))
((0 . "LINE") (100 . "AcDbEntity") (67 . 0) (8 . "A-Window") (62 . 252) (420 . 9868950) (6 . "Continuous") (100 . "AcDbLine") (10 57.4828888398 -47.3049731404 0.0000000000) (11 57.4828888398 -49.3380171897 0.0000000000) (210 0.0000000000 0.0000000000 1.0000000000))
((0 . "LINE") (100 . "AcDbEntity") (67 . 0) (8 . "A-Window") (62 . 252) (420 . 9868950) (6 . "Continuous") (100 . "AcDbLine") (10 60.7741939015 -46.0467121280 0.0000000000) (11 60.7741939015 -46.7967121280 0.0000000000) (210 0.0000000000 0.0000000000 1.0000000000))
((0 . "ARC") (100 . "AcDbEntity") (67 . 0) (8 . "A-Window") (62 . 252) (420 . 9868950) (6 . "Continuous") (100 . "AcDbCircle") (10 58.7597393699 -45.5172243919 0.0000000000) (40 . 0.5295876191) (210 0.0000000000 0.0000000000 1.0000000000) (100 . "AcDbArc") (50 . 3.0398793474) (51 . -1.5902185321))
((0 . "LINE") (100 . "AcDbEntity") (67 . 0) (8 . "A-Window") (62 . 252) (420 . 9868950) (6 . "Continuous") (100 . "AcDbLine") (10 60.7741939015 -46.0467121280 0.0000000000) (11 58.7494542571 -46.0467121280 0.0000000000) (210 0.0000000000 0.0000000000 1.0000000000))
((0 . "ARC") (100 . "AcDbEntity") (67 . 0) (8 . "A-Window") (62 . 252) (420 . 9868950) (6 . "Continuous") (100 . "AcDbCircle") (10 58.7007738119 -47.2638695594 0.0000000000) (40 . 0.4696869718) (210 0.0000000000 0.0000000000 1.0000000000) (100 . "AcDbArc") (50 . 1.4669654186) (51 . -3.0539678520))
((0 . "LINE") (100 . "AcDbEntity") (67 . 0) (8 . "A-Window") (62 . 252) (420 . 9868950) (6 . "Continuous") (100 . "AcDbLine") (10 60.7741939015 -46.7967121280 0.0000000000) (11 58.7494542571 -46.7967121280 0.0000000000) (210 0.0000000000 0.0000000000 1.0000000000))
((0 . "LINE") (100 . "AcDbEntity") (67 . 0) (8 . "A-Window") (62 . 252) (420 . 9868950) (6 . "Continuous") (100 . "AcDbLine") (10 58.2328888398 -47.3049731404 0.0000000000) (11 58.2328888398 -49.3380171897 0.0000000000) (210 0.0000000000 0.0000000000 1.0000000000))
((0 . "LINE") (100 . "AcDbEntity") (67 . 0) (8 . "A-Window") (62 . 252) (420 . 9868950) (6 . "Continuous") (100 . "AcDbLine") (10 58.2328888398 -49.3380171897 0.0000000000) (11 57.4828888398 -49.3380171897 0.0000000000) (210 0.0000000000 0.0000000000 1.0000000000))
((0 . "LINE") (100 . "AcDbEntity") (67 . 0) (8 . "A-Window") (62 . 252) (420 . 9868950) (6 . "Continuous") (100 . "AcDbLine") (10 58.2328888398 -43.5054070663 0.0000000000) (11 57.4828888398 -43.5054070663 0.0000000000) (210 0.0000000000 0.0000000000 1.0000000000))
((0 . "LINE") (100 . "AcDbEntity") (67 . 0) (8 . "A-Window") (62 . 252) (420 . 9868950) (6 . "Continuous") (100 . "AcDbLine") (10 57.4828888398 -43.5054070663 0.0000000000) (11 57.4828888398 -45.4634511157 0.0000000000) (210 0.0000000000 0.0000000000 1.0000000000))
((0 . "LINE") (100 . "AcDbEntity") (67 . 0) (8 . "A-Window") (62 . 252) (420 . 9868950) (6 . "Continuous") (100 . "AcDbLine") (10 58.2328888398 -43.5054070663 0.0000000000) (11 58.2328888398 -45.4634511157 0.0000000000) (210 0.0000000000 0.0000000000 1.0000000000))
((0 . "LINE") (100 . "AcDbEntity") (67 . 0) (8 . "A-Window") (62 . 252) (420 . 9868950) (6 . "Continuous") (100 . "AcDbLine") (10 54.9415837781 -46.0467121280 0.0000000000) (11 54.9415837781 -46.7967121280 0.0000000000) (210 0.0000000000 0.0000000000 1.0000000000))
((0 . "LINE") (100 . "AcDbEntity") (67 . 0) (8 . "A-Window") (62 . 252) (420 . 9868950) (6 . "Continuous") (100 . "AcDbLine") (10 56.8996278275 -46.0467121280 0.0000000000) (11 54.9415837781 -46.0467121280 0.0000000000) (210 0.0000000000 0.0000000000 1.0000000000))
((0 . "LINE") (100 . "AcDbEntity") (67 . 0) (8 . "A-Window") (62 . 252) (420 . 9868950) (6 . "Continuous") (100 . "AcDbLine") (10 56.8996278275 -46.7967121280 0.0000000000) (11 54.9415837781 -46.7967121280 0.0000000000) (210 0.0000000000 0.0000000000 1.0000000000))
((0 . "LINE") (100 . "AcDbEntity") (67 . 0) (8 . "A-Window") (62 . 8) (6 . "CENTER") (48 . 0.5000000000) (100 . "AcDbLine") (10 62.8578888398 45.5782878720 0.0000000000) (11 52.8578888398 45.5782878720 0.0000000000) (210 0.0000000000 0.0000000000 1.0000000000))
((0 . "ARC") (100 . "AcDbEntity") (67 . 0) (8 . "A-Window") (62 . 252) (420 . 9868950) (6 . "Continuous") (100 . "AcDbCircle") (10 -56.8996278275 44.6200268596 0.0000000000) (40 . 0.5832610123) (210 0.0000000000 0.0000000000 -1.0000000000) (100 . "AcDbArc") (50 . 1.5707963268) (51 . 3.1415926536))
((0 . "ARC") (100 . "AcDbEntity") (67 . 0) (8 . "A-Window") (62 . 252) (420 . 9868950) (6 . "Continuous") (100 . "AcDbCircle") (10 -56.9596580479 46.4731940600 0.0000000000) (40 . 0.5233603650) (210 0.0000000000 0.0000000000 -1.0000000000) (100 . "AcDbArc") (50 . -3.1193400384) (51 . -1.4558418125))
((0 . "CIRCLE") (100 . "AcDbEntity") (67 . 0) (8 . "A-Window") (62 . 252) (420 . 9868950) (6 . "Continuous") (100 . "AcDbCircle") (10 -57.8578888398 45.5782878720 0.0000000000) (40 . 4.0000000000) (210 0.0000000000 0.0000000000 -1.0000000000))
((0 . "LINE") (100 . "AcDbEntity") (67 . 0) (8 . "A-Window") (62 . 8) (6 . "CENTER") (48 . 0.5000000000) (100 . "AcDbLine") (10 57.8578888398 40.5782878720 0.0000000000) (11 57.8578888398 50.5782878720 0.0000000000) (210 0.0000000000 0.0000000000 1.0000000000))
((0 . "LINE") (100 . "AcDbEntity") (67 . 0) (8 . "A-Window") (62 . 252) (420 . 9868950) (6 . "Continuous") (100 . "AcDbLine") (10 57.4828888398 46.4615488843 0.0000000000) (11 57.4828888398 48.4945929337 0.0000000000) (210 0.0000000000 0.0000000000 1.0000000000))
((0 . "LINE") (100 . "AcDbEntity") (67 . 0) (8 . "A-Window") (62 . 252) (420 . 9868950) (6 . "Continuous") (100 . "AcDbLine") (10 60.7741939015 45.2032878720 0.0000000000) (11 60.7741939015 45.9532878720 0.0000000000) (210 0.0000000000 0.0000000000 1.0000000000))
((0 . "ARC") (100 . "AcDbEntity") (67 . 0) (8 . "A-Window") (62 . 252) (420 . 9868950) (6 . "Continuous") (100 . "AcDbCircle") (10 -58.7597393699 44.6738001358 0.0000000000) (40 . 0.5295876191) (210 0.0000000000 0.0000000000 -1.0000000000) (100 . "AcDbArc") (50 . -0.1017133062) (51 . 1.5513741215))
((0 . "LINE") (100 . "AcDbEntity") (67 . 0) (8 . "A-Window") (62 . 252) (420 . 9868950) (6 . "Continuous") (100 . "AcDbLine") (10 60.7741939015 45.2032878720 0.0000000000) (11 58.7494542571 45.2032878720 0.0000000000) (210 0.0000000000 0.0000000000 1.0000000000))
((0 . "ARC") (100 . "AcDbEntity") (67 . 0) (8 . "A-Window") (62 . 252) (420 . 9868950) (6 . "Continuous") (100 . "AcDbCircle") (10 -58.7007738119 46.4204453034 0.0000000000) (40 . 0.4696869718) (210 0.0000000000 0.0000000000 -1.0000000000) (100 . "AcDbArc") (50 . -1.6746272350) (51 . 0.0876248016))
((0 . "LINE") (100 . "AcDbEntity") (67 . 0) (8 . "A-Window") (62 . 252) (420 . 9868950) (6 . "Continuous") (100 . "AcDbLine") (10 60.7741939015 45.9532878720 0.0000000000) (11 58.7494542571 45.9532878720 0.0000000000) (210 0.0000000000 0.0000000000 1.0000000000))
((0 . "LINE") (100 . "AcDbEntity") (67 . 0) (8 . "A-Window") (62 . 252) (420 . 9868950) (6 . "Continuous") (100 . "AcDbLine") (10 58.2328888398 46.4615488843 0.0000000000) (11 58.2328888398 48.4945929337 0.0000000000) (210 0.0000000000 0.0000000000 1.0000000000))
((0 . "LINE") (100 . "AcDbEntity") (67 . 0) (8 . "A-Window") (62 . 252) (420 . 9868950) (6 . "Continuous") (100 . "AcDbLine") (10 58.2328888398 48.4945929337 0.0000000000) (11 57.4828888398 48.4945929337 0.0000000000) (210 0.0000000000 0.0000000000 1.0000000000))
((0 . "LINE") (100 . "AcDbEntity") (67 . 0) (8 . "A-Window") (62 . 252) (420 . 9868950) (6 . "Continuous") (100 . "AcDbLine") (10 58.2328888398 42.6619828103 0.0000000000) (11 57.4828888398 42.6619828103 0.0000000000) (210 0.0000000000 0.0000000000 1.0000000000))
((0 . "LINE") (100 . "AcDbEntity") (67 . 0) (8 . "A-Window") (62 . 252) (420 . 9868950) (6 . "Continuous") (100 . "AcDbLine") (10 57.4828888398 42.6619828103 0.0000000000) (11 57.4828888398 44.6200268596 0.0000000000) (210 0.0000000000 0.0000000000 1.0000000000))
((0 . "LINE") (100 . "AcDbEntity") (67 . 0) (8 . "A-Window") (62 . 252) (420 . 9868950) (6 . "Continuous") (100 . "AcDbLine") (10 58.2328888398 42.6619828103 0.0000000000) (11 58.2328888398 44.6200268596 0.0000000000) (210 0.0000000000 0.0000000000 1.0000000000))
((0 . "LINE") (100 . "AcDbEntity") (67 . 0) (8 . "A-Window") (62 . 252) (420 . 9868950) (6 . "Continuous") (100 . "AcDbLine") (10 54.9415837781 45.2032878720 0.0000000000) (11 54.9415837781 45.9532878720 0.0000000000) (210 0.0000000000 0.0000000000 1.0000000000))
((0 . "LINE") (100 . "AcDbEntity") (67 . 0) (8 . "A-Window") (62 . 252) (420 . 9868950) (6 . "Continuous") (100 . "AcDbLine") (10 56.8996278275 45.2032878720 0.0000000000) (11 54.9415837781 45.2032878720 0.0000000000) (210 0.0000000000 0.0000000000 1.0000000000))
((0 . "LINE") (100 . "AcDbEntity") (67 . 0) (8 . "A-Window") (62 . 252) (420 . 9868950) (6 . "Continuous") (100 . "AcDbLine") (10 56.8996278275 45.9532878720 0.0000000000) (11 54.9415837781 45.9532878720 0.0000000000) (210 0.0000000000 0.0000000000 1.0000000000))
((0 . "LINE") (100 . "AcDbEntity") (67 . 0) (8 . "A-Window") (62 . 8) (6 . "CENTER") (48 . 0.5000000000) (100 . "AcDbLine") (10 137.8578888398 -46.4217121280 0.0000000000) (11 127.8578888398 -46.4217121280 0.0000000000) (210 0.0000000000 0.0000000000 1.0000000000))
((0 . "ARC") (100 . "AcDbEntity") (67 . 0) (8 . "A-Window") (62 . 252) (420 . 9868950) (6 . "Continuous") (100 . "AcDbCircle") (10 131.8996278275 -45.4634511157 0.0000000000) (40 . 0.5832610123) (210 0.0000000000 0.0000000000 1.0000000000) (100 . "AcDbArc") (50 . -1.5707963268) (51 . 0.0000000000))
((0 . "ARC") (100 . "AcDbEntity") (67 . 0) (8 . "A-Window") (62 . 252) (420 . 9868950) (6 . "Continuous") (100 . "AcDbCircle") (10 131.9596580479 -47.3166183160 0.0000000000) (40 . 0.5233603650) (210 0.0000000000 0.0000000000 1.0000000000) (100 . "AcDbArc") (50 . 0.0222526151) (51 . 1.6857508410))
((0 . "CIRCLE") (100 . "AcDbEntity") (67 . 0) (8 . "A-Window") (62 . 252) (420 . 9868950) (6 . "Continuous") (100 . "AcDbCircle") (10 132.8578888398 -46.4217121280 0.0000000000) (40 . 4.0000000000) (210 0.0000000000 0.0000000000 1.0000000000))
((0 . "LINE") (100 . "AcDbEntity") (67 . 0) (8 . "A-Window") (62 . 8) (6 . "CENTER") (48 . 0.5000000000) (100 . "AcDbLine") (10 132.8578888398 -41.4217121280 0.0000000000) (11 132.8578888398 -51.4217121280 0.0000000000) (210 0.0000000000 0.0000000000 1.0000000000))
((0 . "LINE") (100 . "AcDbEntity") (67 . 0) (8 . "A-Window") (62 . 252) (420 . 9868950) (6 . "Continuous") (100 . "AcDbLine") (10 132.4828888398 -47.3049731404 0.0000000000) (11 132.4828888398 -49.3380171897 0.0000000000) (210 0.0000000000 0.0000000000 1.0000000000))
((0 . "LINE") (100 . "AcDbEntity") (67 . 0) (8 . "A-Window") (62 . 252) (420 . 9868950) (6 . "Continuous") (100 . "AcDbLine") (10 135.7741939015 -46.0467121280 0.0000000000) (11 135.7741939015 -46.7967121280 0.0000000000) (210 0.0000000000 0.0000000000 1.0000000000))
((0 . "ARC") (100 . "AcDbEntity") (67 . 0) (8 . "A-Window") (62 . 252) (420 . 9868950) (6 . "Continuous") (100 . "AcDbCircle") (10 133.7597393699 -45.5172243919 0.0000000000) (40 . 0.5295876191) (210 0.0000000000 0.0000000000 1.0000000000) (100 . "AcDbArc") (50 . 3.0398793474) (51 . -1.5902185321))
((0 . "LINE") (100 . "AcDbEntity") (67 . 0) (8 . "A-Window") (62 . 252) (420 . 9868950) (6 . "Continuous") (100 . "AcDbLine") (10 135.7741939015 -46.0467121280 0.0000000000) (11 133.7494542571 -46.0467121280 0.0000000000) (210 0.0000000000 0.0000000000 1.0000000000))
((0 . "ARC") (100 . "AcDbEntity") (67 . 0) (8 . "A-Window") (62 . 252) (420 . 9868950) (6 . "Continuous") (100 . "AcDbCircle") (10 133.7007738119 -47.2638695594 0.0000000000) (40 . 0.4696869718) (210 0.0000000000 0.0000000000 1.0000000000) (100 . "AcDbArc") (50 . 1.4669654186) (51 . -3.0539678520))
((0 . "LINE") (100 . "AcDbEntity") (67 . 0) (8 . "A-Window") (62 . 252) (420 . 9868950) (6 . "Continuous") (100 . "AcDbLine") (10 135.7741939015 -46.7967121280 0.0000000000) (11 133.7494542571 -46.7967121280 0.0000000000) (210 0.0000000000 0.0000000000 1.0000000000))
((0 . "LINE") (100 . "AcDbEntity") (67 . 0) (8 . "A-Window") (62 . 252) (420 . 9868950) (6 . "Continuous") (100 . "AcDbLine") (10 133.2328888398 -47.3049731404 0.0000000000) (11 133.2328888398 -49.3380171897 0.0000000000) (210 0.0000000000 0.0000000000 1.0000000000))
((0 . "LINE") (100 . "AcDbEntity") (67 . 0) (8 . "A-Window") (62 . 252) (420 . 9868950) (6 . "Continuous") (100 . "AcDbLine") (10 133.2328888398 -49.3380171897 0.0000000000) (11 132.4828888398 -49.3380171897 0.0000000000) (210 0.0000000000 0.0000000000 1.0000000000))
((0 . "LINE") (100 . "AcDbEntity") (67 . 0) (8 . "A-Window") (62 . 252) (420 . 9868950) (6 . "Continuous") (100 . "AcDbLine") (10 133.2328888398 -43.5054070663 0.0000000000) (11 132.4828888398 -43.5054070663 0.0000000000) (210 0.0000000000 0.0000000000 1.0000000000))
((0 . "LINE") (100 . "AcDbEntity") (67 . 0) (8 . "A-Window") (62 . 252) (420 . 9868950) (6 . "Continuous") (100 . "AcDbLine") (10 132.4828888398 -43.5054070663 0.0000000000) (11 132.4828888398 -45.4634511157 0.0000000000) (210 0.0000000000 0.0000000000 1.0000000000))
((0 . "LINE") (100 . "AcDbEntity") (67 . 0) (8 . "A-Window") (62 . 252) (420 . 9868950) (6 . "Continuous") (100 . "AcDbLine") (10 133.2328888398 -43.5054070663 0.0000000000) (11 133.2328888398 -45.4634511157 0.0000000000) (210 0.0000000000 0.0000000000 1.0000000000))
((0 . "LINE") (100 . "AcDbEntity") (67 . 0) (8 . "A-Window") (62 . 252) (420 . 9868950) (6 . "Continuous") (100 . "AcDbLine") (10 129.9415837781 -46.0467121280 0.0000000000) (11 129.9415837781 -46.7967121280 0.0000000000) (210 0.0000000000 0.0000000000 1.0000000000))
((0 . "LINE") (100 . "AcDbEntity") (67 . 0) (8 . "A-Window") (62 . 252) (420 . 9868950) (6 . "Continuous") (100 . "AcDbLine") (10 131.8996278275 -46.0467121280 0.0000000000) (11 129.9415837781 -46.0467121280 0.0000000000) (210 0.0000000000 0.0000000000 1.0000000000))
((0 . "LINE") (100 . "AcDbEntity") (67 . 0) (8 . "A-Window") (62 . 252) (420 . 9868950) (6 . "Continuous") (100 . "AcDbLine") (10 131.8996278275 -46.7967121280 0.0000000000) (11 129.9415837781 -46.7967121280 0.0000000000) (210 0.0000000000 0.0000000000 1.0000000000))
((0 . "LINE") (100 . "AcDbEntity") (67 . 0) (8 . "A-Window") (62 . 8) (6 . "CENTER") (48 . 0.5000000000) (100 . "AcDbLine") (10 137.8578888398 45.5782878720 0.0000000000) (11 127.8578888398 45.5782878720 0.0000000000) (210 0.0000000000 0.0000000000 1.0000000000))
((0 . "ARC") (100 . "AcDbEntity") (67 . 0) (8 . "A-Window") (62 . 252) (420 . 9868950) (6 . "Continuous") (100 . "AcDbCircle") (10 -131.8996278275 44.6200268596 0.0000000000) (40 . 0.5832610123) (210 0.0000000000 0.0000000000 -1.0000000000) (100 . "AcDbArc") (50 . 1.5707963268) (51 . 3.1415926536))
((0 . "ARC") (100 . "AcDbEntity") (67 . 0) (8 . "A-Window") (62 . 252) (420 . 9868950) (6 . "Continuous") (100 . "AcDbCircle") (10 -131.9596580479 46.4731940600 0.0000000000) (40 . 0.5233603650) (210 0.0000000000 0.0000000000 -1.0000000000) (100 . "AcDbArc") (50 . -3.1193400384) (51 . -1.4558418125))
((0 . "CIRCLE") (100 . "AcDbEntity") (67 . 0) (8 . "A-Window") (62 . 252) (420 . 9868950) (6 . "Continuous") (100 . "AcDbCircle") (10 -132.8578888398 45.5782878720 0.0000000000) (40 . 4.0000000000) (210 0.0000000000 0.0000000000 -1.0000000000))
((0 . "LINE") (100 . "AcDbEntity") (67 . 0) (8 . "A-Window") (62 . 8) (6 . "CENTER") (48 . 0.5000000000) (100 . "AcDbLine") (10 132.8578888398 40.5782878720 0.0000000000) (11 132.8578888398 50.5782878720 0.0000000000) (210 0.0000000000 0.0000000000 1.0000000000))
((0 . "LINE") (100 . "AcDbEntity") (67 . 0) (8 . "A-Window") (62 . 252) (420 . 9868950) (6 . "Continuous") (100 . "AcDbLine") (10 132.4828888398 46.4615488843 0.0000000000) (11 132.4828888398 48.4945929337 0.0000000000) (210 0.0000000000 0.0000000000 1.0000000000))
((0 . "LINE") (100 . "AcDbEntity") (67 . 0) (8 . "A-Window") (62 . 252) (420 . 9868950) (6 . "Continuous") (100 . "AcDbLine") (10 135.7741939015 45.2032878720 0.0000000000) (11 135.7741939015 45.9532878720 0.0000000000) (210 0.0000000000 0.0000000000 1.0000000000))
((0 . "ARC") (100 . "AcDbEntity") (67 . 0) (8 . "A-Window") (62 . 252) (420 . 9868950) (6 . "Continuous") (100 . "AcDbCircle") (10 -133.7597393699 44.6738001358 0.0000000000) (40 . 0.5295876191) (210 0.0000000000 0.0000000000 -1.0000000000) (100 . "AcDbArc") (50 . -0.1017133062) (51 . 1.5513741215))
((0 . "LINE") (100 . "AcDbEntity") (67 . 0) (8 . "A-Window") (62 . 252) (420 . 9868950) (6 . "Continuous") (100 . "AcDbLine") (10 135.7741939015 45.2032878720 0.0000000000) (11 133.7494542571 45.2032878720 0.0000000000) (210 0.0000000000 0.0000000000 1.0000000000))
((0 . "ARC") (100 . "AcDbEntity") (67 . 0) (8 . "A-Window") (62 . 252) (420 . 9868950) (6 . "Continuous") (100 . "AcDbCircle") (10 -133.7007738119 46.4204453034 0.0000000000) (40 . 0.4696869718) (210 0.0000000000 0.0000000000 -1.0000000000) (100 . "AcDbArc") (50 . -1.6746272350) (51 . 0.0876248016))
((0 . "LINE") (100 . "AcDbEntity") (67 . 0) (8 . "A-Window") (62 . 252) (420 . 9868950) (6 . "Continuous") (100 . "AcDbLine") (10 135.7741939015 45.9532878720 0.0000000000) (11 133.7494542571 45.9532878720 0.0000000000) (210 0.0000000000 0.0000000000 1.0000000000))
((0 . "LINE") (100 . "AcDbEntity") (67 . 0) (8 . "A-Window") (62 . 252) (420 . 9868950) (6 . "Continuous") (100 . "AcDbLine") (10 133.2328888398 46.4615488843 0.0000000000) (11 133.2328888398 48.4945929337 0.0000000000) (210 0.0000000000 0.0000000000 1.0000000000))
((0 . "LINE") (100 . "AcDbEntity") (67 . 0) (8 . "A-Window") (62 . 252) (420 . 9868950) (6 . "Continuous") (100 . "AcDbLine") (10 133.2328888398 48.4945929337 0.0000000000) (11 132.4828888398 48.4945929337 0.0000000000) (210 0.0000000000 0.0000000000 1.0000000000))
((0 . "LINE") (100 . "AcDbEntity") (67 . 0) (8 . "A-Window") (62 . 252) (420 . 9868950) (6 . "Continuous") (100 . "AcDbLine") (10 133.2328888398 42.6619828103 0.0000000000) (11 132.4828888398 42.6619828103 0.0000000000) (210 0.0000000000 0.0000000000 1.0000000000))
((0 . "LINE") (100 . "AcDbEntity") (67 . 0) (8 . "A-Window") (62 . 252) (420 . 9868950) (6 . "Continuous") (100 . "AcDbLine") (10 132.4828888398 42.6619828103 0.0000000000) (11 132.4828888398 44.6200268596 0.0000000000) (210 0.0000000000 0.0000000000 1.0000000000))
((0 . "LINE") (100 . "AcDbEntity") (67 . 0) (8 . "A-Window") (62 . 252) (420 . 9868950) (6 . "Continuous") (100 . "AcDbLine") (10 133.2328888398 42.6619828103 0.0000000000) (11 133.2328888398 44.6200268596 0.0000000000) (210 0.0000000000 0.0000000000 1.0000000000))
((0 . "LINE") (100 . "AcDbEntity") (67 . 0) (8 . "A-Window") (62 . 252) (420 . 9868950) (6 . "Continuous") (100 . "AcDbLine") (10 129.9415837781 45.2032878720 0.0000000000) (11 129.9415837781 45.9532878720 0.0000000000) (210 0.0000000000 0.0000000000 1.0000000000))
((0 . "LINE") (100 . "AcDbEntity") (67 . 0) (8 . "A-Window") (62 . 252) (420 . 9868950) (6 . "Continuous") (100 . "AcDbLine") (10 131.8996278275 45.2032878720 0.0000000000) (11 129.9415837781 45.2032878720 0.0000000000) (210 0.0000000000 0.0000000000 1.0000000000))
((0 . "LINE") (100 . "AcDbEntity") (67 . 0) (8 . "A-Window") (62 . 252) (420 . 9868950) (6 . "Continuous") (100 . "AcDbLine") (10 131.8996278275 45.9532878720 0.0000000000) (11 129.9415837781 45.9532878720 0.0000000000) (210 0.0000000000 0.0000000000 1.0000000000))
((0 . "LWPOLYLINE") (100 . "AcDbEntity") (67 . 0) (8 . "A-Window") (62 . 252) (420 . 9868950) (6 . "Continuous") (100 . "AcDbPolyline") (90 . 4) (70 . 1) (43 . 0.0000000000) (38 . 0.0000000000) (39 . 0.0000000000) (10 -32.8578888398 -15.9217121281) (40 . 0.0000000000) (41 . 0.0000000000) (42 . 0.0000000000) (91 . 0) (10 -194.8578888398 -15.9217121281) (40 . 0.0000000000) (41 . 0.0000000000) (42 . 0.0000000000) (91 . 0) (10 -194.8578888398 -8.9217121281) (40 . 0.0000000000) (41 . 0.0000000000) (42 . 0.0000000000) (91 . 0) (10 -32.8578888398 -8.9217121281) (40 . 0.0000000000) (41 . 0.0000000000) (42 . 0.0000000000) (91 . 0) (210 0.0000000000 0.0000000000 -1.0000000000))
((0 . "LWPOLYLINE") (100 . "AcDbEntity") (67 . 0) (8 . "A-Window") (62 . 252) (420 . 9868950) (6 . "Continuous") (100 . "AcDbPolyline") (90 . 4) (70 . 1) (43 . 0.0000000000) (38 . 0.0000000000) (39 . 0.0000000000) (10 -32.8578888398 15.0782878721) (40 . 0.0000000000) (41 . 0.0000000000) (42 . 0.0000000000) (91 . 0) (10 -194.8578888398 15.0782878721) (40 . 0.0000000000) (41 . 0.0000000000) (42 . 0.0000000000) (91 . 0) (10 -194.8578888398 8.0782878721) (40 . 0.0000000000) (41 . 0.0000000000) (42 . 0.0000000000) (91 . 0) (10 -32.8578888398 8.0782878721) (40 . 0.0000000000) (41 . 0.0000000000) (42 . 0.0000000000) (91 . 0) (210 0.0000000000 0.0000000000 -1.0000000000))
((0 . "CIRCLE") (100 . "AcDbEntity") (67 . 0) (8 . "A-Window") (62 . 252) (420 . 9868950) (6 . "Continuous") (100 . "AcDbCircle") (10 -75.8578888398 -2.6287009723 0.0000000000) (40 . 10.1131438220) (210 0.0000000000 0.0000000000 -1.0000000000))
((0 . "CIRCLE") (100 . "AcDbEntity") (67 . 0) (8 . "A-Window") (62 . 252) (420 . 9868950) (6 . "Continuous") (100 . "AcDbCircle") (10 -75.8578888398 -2.6287009723 0.0000000000) (40 . 9.1131438220) (210 0.0000000000 0.0000000000 -1.0000000000))
((0 . "LINE") (100 . "AcDbEntity") (67 . 0) (8 . "A-Window") (62 . 252) (420 . 9868950) (6 . "CENTER") (48 . 100.0000000000) (100 . "AcDbLine") (10 56.5618956108 -2.6287009723 0.0000000000) (11 95.1538820690 -2.6287009723 0.0000000000) (210 0.0000000000 0.0000000000 1.0000000000))
((0 . "LINE") (100 . "AcDbEntity") (67 . 0) (8 . "A-Window") (62 . 252) (420 . 9868950) (6 . "CENTER") (48 . 100.0000000000) (100 . "AcDbLine") (10 75.8578888398 -21.9246942014 0.0000000000) (11 75.8578888398 19.6672922568 0.0000000000) (210 0.0000000000 0.0000000000 1.0000000000))
((0 . "LINE") (100 . "AcDbEntity") (67 . 0) (8 . "A-Window") (62 . 252) (420 . 9868950) (6 . "Continuous") (100 . "AcDbLine") (10 32.8578888398 6.8265860749 0.0000000000) (11 32.8578888398 -1.9217121280 0.0000000000) (210 0.0000000000 0.0000000000 1.0000000000))
((0 . "LINE") (100 . "AcDbEntity") (67 . 0) (8 . "A-Window") (62 . 148) (6 . "Continuous") (100 . "AcDbLine") (10 730.7012894638 -10.9920844850 0.0000000000) (11 730.7012894638 -46.1720844849 0.0000000000) (210 0.0000000000 0.0000000000 1.0000000000))
((0 . "CIRCLE") (100 . "AcDbEntity") (67 . 0) (8 . "A-Window") (62 . 148) (6 . "Continuous") (100 . "AcDbCircle") (10 -745.5450394638 -65.1720844847 0.0000000000) (40 . 19.0000000000) (210 0.0000000000 0.0000000000 -1.0000000000))
((0 . "LINE") (100 . "AcDbEntity") (67 . 0) (8 . "A-Window") (62 . 148) (6 . "Continuous") (100 . "AcDbLine") (10 730.7012894638 -10.9920844850 0.0000000000) (11 730.7012894638 -53.3119375233 0.0000000000) (210 0.0000000000 0.0000000000 1.0000000000))
((0 . "LINE") (100 . "AcDbEntity") (67 . 0) (8 . "A-Window") (62 . 148) (6 . "Continuous") (100 . "AcDbLine") (10 760.3887894638 -10.9920844850 0.0000000000) (11 760.3887894638 -53.3119375233 0.0000000000) (210 0.0000000000 0.0000000000 1.0000000000))
((0 . "LWPOLYLINE") (100 . "AcDbEntity") (67 . 0) (8 . "A-Window") (62 . 148) (6 . "Continuous") (100 . "AcDbPolyline") (90 . 5) (70 . 0) (43 . 0.0000000000) (38 . 0.0000000000) (39 . 0.0000000000) (10 -768.3730128085 -5.6720844846) (40 . 0.0000000000) (41 . 0.0000000000) (42 . 0.0000000000) (91 . 0) (10 -722.7170661195 -5.6720844848) (40 . 0.0000000000) (41 . 0.0000000000) (42 . -0.2220002644) (91 . 0) (10 -724.7623816823 -7.1920844849) (40 . 0.0000000000) (41 . 0.0000000000) (42 . 0.0000000000) (91 . 0) (10 -766.3276972452 -7.1920844849) (40 . 0.0000000000) (41 . 0.0000000000) (42 . -0.2220002644) (91 . 0) (10 -768.3730128085 -5.6720844846) (40 . 0.0000000000) (41 . 0.0000000000) (42 . 6.7869977914) (91 . 0) (210 0.0000000000 0.0000000000 -1.0000000000))
((0 . "LWPOLYLINE") (100 . "AcDbEntity") (67 . 0) (8 . "A-Window") (62 . 148) (6 . "Continuous") (100 . "AcDbPolyline") (90 . 4) (70 . 0) (43 . 0.0000000000) (38 . 0.0000000000) (39 . 0.0000000000) (10 -724.7623816823 -7.1920844849) (40 . 0.0000000000) (41 . 0.0000000000) (42 . -0.2225651805) (91 . 0) (10 -726.8076972452 -10.9920844850) (40 . 0.0000000000) (41 . 0.0000000000) (42 . 0.0000000000) (91 . 0) (10 -764.2823816824 -10.9920844850) (40 . 0.0000000000) (41 . 0.0000000000) (42 . -0.2225651805) (91 . 0) (10 -766.3276972452 -7.1920844849) (40 . 0.0000000000) (41 . 0.0000000000) (42 . 1.8579040169) (91 . 0) (210 0.0000000000 0.0000000000 -1.0000000000))
((0 . "LINE") (100 . "AcDbEntity") (67 . 0) (8 . "A-Window") (62 . 148) (6 . "Continuous") (100 . "AcDbLine") (10 730.7012894638 11.6479155154 0.0000000000) (11 730.7012894638 48.3279155153 0.0000000000) (210 0.0000000000 0.0000000000 1.0000000000))
((0 . "CIRCLE") (100 . "AcDbEntity") (67 . 0) (8 . "A-Window") (62 . 148) (6 . "Continuous") (100 . "AcDbCircle") (10 -745.5450394638 67.3279155153 0.0000000000) (40 . 19.0000000000) (210 0.0000000000 0.0000000000 -1.0000000000))
((0 . "LINE") (100 . "AcDbEntity") (67 . 0) (8 . "A-Window") (62 . 148) (6 . "Continuous") (100 . "AcDbLine") (10 730.7012894638 11.6479155154 0.0000000000) (11 730.7012894638 55.4677685538 0.0000000000) (210 0.0000000000 0.0000000000 1.0000000000))
((0 . "LINE") (100 . "AcDbEntity") (67 . 0) (8 . "A-Window") (62 . 148) (6 . "Continuous") (100 . "AcDbLine") (10 760.3887894638 11.6479155154 0.0000000000) (11 760.3887894638 55.4677685538 0.0000000000) (210 0.0000000000 0.0000000000 1.0000000000))
((0 . "LWPOLYLINE") (100 . "AcDbEntity") (67 . 0) (8 . "A-Window") (62 . 148) (6 . "Continuous") (100 . "AcDbPolyline") (90 . 5) (70 . 0) (43 . 0.0000000000) (38 . 0.0000000000) (39 . 0.0000000000) (10 -768.3730128085 6.3279155151) (40 . 0.0000000000) (41 . 0.0000000000) (42 . 0.0000000000) (91 . 0) (10 -722.7170661195 6.3279155154) (40 . 0.0000000000) (41 . 0.0000000000) (42 . 0.2220002644) (91 . 0) (10 -724.7623816823 7.8479155154) (40 . 0.0000000000) (41 . 0.0000000000) (42 . 0.0000000000) (91 . 0) (10 -766.3276972452 7.8479155154) (40 . 0.0000000000) (41 . 0.0000000000) (42 . 0.2220002644) (91 . 0) (10 -768.3730128085 6.3279155151) (40 . 0.0000000000) (41 . 0.0000000000) (42 . -6.7869977914) (91 . 0) (210 0.0000000000 0.0000000000 -1.0000000000))
((0 . "LWPOLYLINE") (100 . "AcDbEntity") (67 . 0) (8 . "A-Window") (62 . 148) (6 . "Continuous") (100 . "AcDbPolyline") (90 . 4) (70 . 0) (43 . 0.0000000000) (38 . 0.0000000000) (39 . 0.0000000000) (10 -724.7623816823 7.8479155154) (40 . 0.0000000000) (41 . 0.0000000000) (42 . 0.2225651805) (91 . 0) (10 -726.8076972452 11.6479155154) (40 . 0.0000000000) (41 . 0.0000000000) (42 . 0.0000000000) (91 . 0) (10 -764.2823816824 11.6479155154) (40 . 0.0000000000) (41 . 0.0000000000) (42 . 0.2225651805) (91 . 0) (10 -766.3276972452 7.8479155154) (40 . 0.0000000000) (41 . 0.0000000000) (42 . -1.8579040169) (91 . 0) (210 0.0000000000 0.0000000000 -1.0000000000))
((0 . "LWPOLYLINE") (100 . "AcDbEntity") (67 . 0) (8 . "A-Window") (62 . 151) (6 . "Continuous") (100 . "AcDbPolyline") (90 . 8) (70 . 1) (43 . 0.0000000000) (38 . 0.0000000000) (39 . 0.0000000000) (10 1694.8578888398 -90.5967000000) (40 . 0.0000000000) (41 . 0.0000000000) (42 . 0.4142135624) (91 . 0) (10 1695.3578888398 -90.0967000000) (40 . 0.0000000000) (41 . 0.0000000000) (42 . 0.0000000000) (91 . 0) (10 1695.3578888398 30.4967000000) (40 . 0.0000000000) (41 . 0.0000000000) (42 . 0.4142135624) (91 . 0) (10 1694.8578888398 30.9967000000) (40 . 0.0000000000) (41 . 0.0000000000) (42 . 0.0000000000) (91 . 0) (10 1635.8578888398 30.9967000000) (40 . 0.0000000000) (41 . 0.0000000000) (42 . 0.4142135624) (91 . 0) (10 1635.3578888398 30.4967000000) (40 . 0.0000000000) (41 . 0.0000000000) (42 . 0.0000000000) (91 . 0) (10 1635.3578888398 -90.0967000000) (40 . 0.0000000000) (41 . 0.0000000000) (42 . 0.4142135624) (91 . 0) (10 1635.8578888398 -90.5967000000) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 87) (70 . 1) (43 . 0.0000000000) (38 . 0.0000000000) (39 . 0.0000000000) (10 1694.7578888398 34.6967000000) (40 . 0.0000000000) (41 . 0.0000000000) (42 . 0.0000000000) (91 . 0) (10 1694.7578888398 34.4967000000) (40 . 0.0000000000) (41 . 0.0000000000) (42 . -0.4142135624) (91 . 0) (10 1694.2578888398 33.9967000000) (40 . 0.0000000000) (41 . 0.0000000000) (42 . 0.0000000000) (91 . 0) (10 1690.4578888398 33.9967000000) (40 . 0.0000000000) (41 . 0.0000000000) (42 . -0.4142135624) (91 . 0) (10 1689.9578888398 34.4967000000) (40 . 0.0000000000) (41 . 0.0000000000) (42 . 0.0000000000) (91 . 0) (10 1689.9578888398 34.6967000000) (40 . 0.0000000000) (41 . 0.0000000000) (42 . -0.4142135624) (91 . 0) (10 1690.4578888398 35.1967000000) (40 . 0.0000000000) (41 . 0.0000000000) (42 . 0.0000000000) (91 . 0) (10 1690.6578888398 35.1967000000) (40 . 0.0000000000) (41 . 0.0000000000) (42 . 0.4142135624) (91 . 0) (10 1691.1578888398 35.6967000000) (40 . 0.0000000000) (41 . 0.0000000000) (42 . 0.0000000000) (91 . 0) (10 1691.1578888398 35.8967000000) (40 . 0.0000000000) (41 . 0.0000000000) (42 . 0.4142135624) (91 . 0) (10 1690.6578888398 36.3967000000) (40 . 0.0000000000) (41 . 0.0000000000) (42 . 0.0000000000) (91 . 0) (10 1689.2578888398 36.3967000000) (40 . 0.0000000000) (41 . 0.0000000000) (42 . 0.4142135624) (91 . 0) (10 1688.7578888398 35.8967000000) (40 . 0.0000000000) (41 . 0.0000000000) (42 . 0.0000000000) (91 . 0) (10 1688.7578888398 34.4967000000) (40 . 0.0000000000) (41 . 0.0000000000) (42 . -0.4142135624) (91 . 0) (10 1688.2578888398 33.9967000000) (40 . 0.0000000000) (41 . 0.0000000000) (42 . 0.0000000000) (91 . 0) (10 1674.3578888398 33.9967000000) (40 . 0.0000000000) (41 . 0.0000000000) (42 . -0.4142135624) (91 . 0) (10 1673.8578888398 34.4967000000) (40 . 0.0000000000) (41 . 0.0000000000) (42 . 0.0000000000) (91 . 0) (10 1673.8578888398 55.8967000000) (40 . 0.0000000000) (41 . 0.0000000000) (42 . 0.4142135624) (91 . 0) (10 1673.3578888398 56.3967000000) (40 . 0.0000000000) (41 . 0.0000000000) (42 . 0.0000000000) (91 . 0) (10 1671.0578936446 56.3967000000) (40 . 0.0000000000) (41 . 0.0000000000) (42 . 0.0000000000) (91 . 0) (10 1670.0809431617 54.4427990332) (40 . 0.0000000000) (41 . 0.0000000000) (42 . 0.4142135643) (91 . 0) (10 1670.1703858820 54.1744708754) (40 . 0.0000000000) (41 . 0.0000000000) (42 . 0.0000000000) (91 . 0) (10 1670.3492713182 54.0850281587) (40 . 0.0000000000) (41 . 0.0000000000) (42 . -0.4142135643) (91 . 0) (10 1670.4387140385 53.8167000008) (40 . 0.0000000000) (41 . 0.0000000000) (42 . 0.0000000000) (91 . 0) (10 1669.8339926783 52.6072572806) (40 . 0.0000000000) (41 . 0.0000000000) (42 . -0.2840790438) (91 . 0) (10 1669.6551072401 52.4966999997) (40 . 0.0000000000) (41 . 0.0000000000) (42 . 0.0000000000) (91 . 0) (10 1666.0235742648 52.4966999997) (40 . 0.0000000000) (41 . 0.0000000000) (42 . 0.1989123674) (91 . 0) (10 1665.8821529086 52.4381213559) (40 . 0.0000000000) (41 . 0.0000000000) (42 . 0.0000000000) (91 . 0) (10 1665.4993101961 52.0552786434) (40 . 0.0000000000) (41 . 0.0000000000) (42 . -0.1989123674) (91 . 0) (10 1665.3578888399 51.9966999997) (40 . 0.0000000000) (41 . 0.0000000000) (42 . -0.1989123674) (91 . 0) (10 1665.2164674837 52.0552786434) (40 . 0.0000000000) (41 . 0.0000000000) (42 . 0.0000000000) (91 . 0) (10 1664.8336247712 52.4381213559) (40 . 0.0000000000) (41 . 0.0000000000) (42 . 0.1989123674) (91 . 0) (10 1664.6922034149 52.4966999997) (40 . 0.0000000000) (41 . 0.0000000000) (42 . 0.0000000000) (91 . 0) (10 1661.0606704397 52.4966999997) (40 . 0.0000000000) (41 . 0.0000000000) (42 . -0.2840790438) (91 . 0) (10 1660.8817850016 52.6072572805) (40 . 0.0000000000) (41 . 0.0000000000) (42 . 0.0000000000) (91 . 0) (10 1660.2770636411 53.8167000007) (40 . 0.0000000000) (41 . 0.0000000000) (42 . -0.4142135642) (91 . 0) (10 1660.3665063613 54.0850281586) (40 . 0.0000000000) (41 . 0.0000000000) (42 . 0.0000000000) (91 . 0) (10 1660.5453917978 54.1744708755) (40 . 0.0000000000) (41 . 0.0000000000) (42 . 0.4142135641) (91 . 0) (10 1660.6348345180 54.4427990333) (40 . 0.0000000000) (41 . 0.0000000000) (42 . 0.0000000000) (91 . 0) (10 1659.6578840351 56.3967000000) (40 . 0.0000000000) (41 . 0.0000000000) (42 . 0.0000000000) (91 . 0) (10 1657.3578888398 56.3967000000) (40 . 0.0000000000) (41 . 0.0000000000) (42 . 0.4142135624) (91 . 0) (10 1656.8578888398 55.8967000000) (40 . 0.0000000000) (41 . 0.0000000000) (42 . 0.0000000000) (91 . 0) (10 1656.8578888398 34.4967000000) (40 . 0.0000000000) (41 . 0.0000000000) (42 . -0.4142135624) (91 . 0) (10 1656.3578888398 33.9967000000) (40 . 0.0000000000) (41 . 0.0000000000) (42 . 0.0000000000) (91 . 0) (10 1642.4578888398 33.9967000000) (40 . 0.0000000000) (41 . 0.0000000000) (42 . -0.4142135624) (91 . 0) (10 1641.9578888398 34.4967000000) (40 . 0.0000000000) (41 . 0.0000000000) (42 . 0.0000000000) (91 . 0) (10 1641.9578888398 35.8967000000) (40 . 0.0000000000) (41 . 0.0000000000) (42 . 0.4142135624) (91 . 0) (10 1641.4578888398 36.3967000000) (40 . 0.0000000000) (41 . 0.0000000000) (42 . 0.0000000000) (91 . 0) (10 1640.0578888398 36.3967000000) (40 . 0.0000000000) (41 . 0.0000000000) (42 . 0.4142135624) (91 . 0) (10 1639.5578888398 35.8967000000) (40 . 0.0000000000) (41 . 0.0000000000) (42 . 0.0000000000) (91 . 0) (10 1639.5578888398 35.6967000000) (40 . 0.0000000000) (41 . 0.0000000000) (42 . 0.4142135624) (91 . 0) (10 1640.0578888398 35.1967000000) (40 . 0.0000000000) (41 . 0.0000000000) (42 . 0.0000000000) (91 . 0) (10 1640.2578888398 35.1967000000) (40 . 0.0000000000) (41 . 0.0000000000) (42 . -0.4142135624) (91 . 0) (10 1640.7578888398 34.6967000000) (40 . 0.0000000000) (41 . 0.0000000000) (42 . 0.0000000000) (91 . 0) (10 1640.7578888398 34.4967000000) (40 . 0.0000000000) (41 . 0.0000000000) (42 . -0.4142135624) (91 . 0) (10 1640.2578888398 33.9967000000) (40 . 0.0000000000) (41 . 0.0000000000) (42 . 0.0000000000) (91 . 0) (10 1636.4578888398 33.9967000000) (40 . 0.0000000000) (41 . 0.0000000000) (42 . -0.4142135624) (91 . 0) (10 1635.9578888398 34.4967000000) (40 . 0.0000000000) (41 . 0.0000000000) (42 . 0.0000000000) (91 . 0) (10 1635.9578888398 34.6967000000) (40 . 0.0000000000) (41 . 0.0000000000) (42 . -0.4142135624) (91 . 0) (10 1636.4578888398 35.1967000000) (40 . 0.0000000000) (41 . 0.0000000000) (42 . 0.0000000000) (91 . 0) (10 1636.6578888398 35.1967000000) (40 . 0.0000000000) (41 . 0.0000000000) (42 . 0.4142135624) (91 . 0) (10 1637.1578888398 35.6967000000) (40 . 0.0000000000) (41 . 0.0000000000) (42 . 0.0000000000) (91 . 0) (10 1637.1578888398 35.8967000000) (40 . 0.0000000000) (41 . 0.0000000000) (42 . 0.4142135624) (91 . 0) (10 1636.6578888398 36.3967000000) (40 . 0.0000000000) (41 . 0.0000000000) (42 . 0.0000000000) (91 . 0) (10 1634.5578888398 36.3967000000) (40 . 0.0000000000) (41 . 0.0000000000) (42 . -0.4142135624) (91 . 0) (10 1634.0578888398 36.8967000000) (40 . 0.0000000000) (41 . 0.0000000000) (42 . 0.0000000000) (91 . 0) (10 1634.0578888398 37.8967000000) (40 . 0.0000000000) (41 . 0.0000000000) (42 . 0.4142135624) (91 . 0) (10 1633.5578888398 38.3967000000) (40 . 0.0000000000) (41 . 0.0000000000) (42 . 0.0000000000) (91 . 0) (10 1633.3578888398 38.3967000000) (40 . 0.0000000000) (41 . 0.0000000000) (42 . 0.4142135624) (91 . 0) (10 1632.8578888398 37.8967000000) (40 . 0.0000000000) (41 . 0.0000000000) (42 . 0.0000000000) (91 . 0) (10 1632.8578888398 33.9967000000) (40 . 0.0000000000) (41 . 0.0000000000) (42 . 0.0000000000) (91 . 0) (10 1632.8578888398 -93.0967000000) (40 . 0.0000000000) (41 . 0.0000000000) (42 . 0.4142135624) (91 . 0) (10 1633.3578888398 -93.5967000000) (40 . 0.0000000000) (41 . 0.0000000000) (42 . 0.0000000000) (91 . 0) (10 1697.3578888398 -93.5967000000) (40 . 0.0000000000) (41 . 0.0000000000) (42 . 0.4142135624) (91 . 0) (10 1697.8578888398 -93.0967000000) (40 . 0.0000000000) (41 . 0.0000000000) (42 . 0.0000000000) (91 . 0) (10 1697.8578888398 33.9967000000) (40 . 0.0000000000) (41 . 0.0000000000) (42 . 0.0000000000) (91 . 0) (10 1697.8578888398 37.8967000000) (40 . 0.0000000000) (41 . 0.0000000000) (42 . 0.4142135624) (91 . 0) (10 1697.3578888398 38.3967000000) (40 . 0.0000000000) (41 . 0.0000000000) (42 . 0.0000000000) (91 . 0) (10 1697.1578888398 38.3967000000) (40 . 0.0000000000) (41 . 0.0000000000) (42 . 0.4142135624) (91 . 0) (10 1696.6578888398 37.8967000000) (40 . 0.0000000000) (41 . 0.0000000000) (42 . 0.0000000000) (91 . 0) (10 1696.6578888398 36.8967000000) (40 . 0.0000000000) (41 . 0.0000000000) (42 . -0.4142135624) (91 . 0) (10 1696.1578888398 36.3967000000) (40 . 0.0000000000) (41 . 0.0000000000) (42 . 0.0000000000) (91 . 0) (10 1694.0578888398 36.3967000000) (40 . 0.0000000000) (41 . 0.0000000000) (42 . 0.4142135624) (91 . 0) (10 1693.5578888398 35.8967000000) (40 . 0.0000000000) (41 . 0.0000000000) (42 . 0.0000000000) (91 . 0) (10 1693.5578888398 35.6967000000) (40 . 0.0000000000) (41 . 0.0000000000) (42 . 0.4142135624) (91 . 0) (10 1694.0578888398 35.1967000000) (40 . 0.0000000000) (41 . 0.0000000000) (42 . 0.0000000000) (91 . 0) (10 1694.2578888398 35.1967000000) (40 . 0.0000000000) (41 . 0.0000000000) (42 . -0.4142135624) (91 . 0) (210 0.0000000000 0.0000000000 1.0000000000))
((0 . "LWPOLYLINE") (100 . "AcDbEntity") (67 . 0) (8 . "A-Window") (62 . 151) (6 . "Continuous") (100 . "AcDbPolyline") (90 . 17) (70 . 1) (43 . 0.0000000000) (38 . 0.0000000000) (39 . 0.0000000000) (10 1665.3578888399 47.4966999996) (40 . 0.0000000000) (41 . 0.0000000000) (42 . 0.0000000000) (91 . 0) (10 1662.1764239704 47.4966999996) (40 . 0.0000000000) (41 . 0.0000000000) (42 . -0.2914734196) (91 . 0) (10 1661.7232700769 47.7853908688) (40 . 0.0000000000) (41 . 0.0000000000) (42 . 0.0000000000) (91 . 0) (10 1660.8267384577 49.7080091306) (40 . 0.0000000000) (41 . 0.0000000000) (42 . 0.2914734196) (91 . 0) (10 1660.3735845642 49.9966999997) (40 . 0.0000000000) (41 . 0.0000000000) (42 . 0.0000000000) (91 . 0) (10 1659.3578888399 49.9966999997) (40 . 0.0000000000) (41 . 0.0000000000) (42 . 0.4142135624) (91 . 0) (10 1658.8578888399 49.4966999997) (40 . 0.0000000000) (41 . 0.0000000000) (42 . 0.0000000000) (91 . 0) (10 1658.8578888399 34.4967000000) (40 . 0.0000000000) (41 . 0.0000000000) (42 . 0.4142135624) (91 . 0) (10 1659.3578888399 33.9967000000) (40 . 0.0000000000) (41 . 0.0000000000) (42 . 0.0000000000) (91 . 0) (10 1671.3578888399 33.9967000000) (40 . 0.0000000000) (41 . 0.0000000000) (42 . 0.4142135624) (91 . 0) (10 1671.8578888399 34.4967000000) (40 . 0.0000000000) (41 . 0.0000000000) (42 . 0.0000000000) (91 . 0) (10 1671.8578888399 49.4966999997) (40 . 0.0000000000) (41 . 0.0000000000) (42 . 0.4142135624) (91 . 0) (10 1671.3578888399 49.9966999997) (40 . 0.0000000000) (41 . 0.0000000000) (42 . 0.0000000000) (91 . 0) (10 1670.3421931158 49.9966999997) (40 . 0.0000000000) (41 . 0.0000000000) (42 . 0.2914734196) (91 . 0) (10 1669.8890392223 49.7080091306) (40 . 0.0000000000) (41 . 0.0000000000) (42 . 0.0000000000) (91 . 0) (10 1668.9925076031 47.7853908688) (40 . 0.0000000000) (41 . 0.0000000000) (42 . -0.2914734196) (91 . 0) (10 1668.5393537096 47.4966999996) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 12) (70 . 1) (43 . 0.0000000000) (38 . 0.0000000000) (39 . 0.0000000000) (10 1671.1467510530 61.6983038651) (40 . 0.0000000000) (41 . 0.0000000000) (42 . 0.2849552787) (91 . 0) (10 1671.2578888323 61.8774783771) (40 . 0.0000000000) (41 . 0.0000000000) (42 . 0.0000000000) (91 . 0) (10 1671.2578888323 61.7734539608) (40 . 0.0000000000) (41 . 0.0000000000) (42 . 0.5564744028) (91 . 0) (10 1670.5357332805 62.2213902406) (40 . 0.0000000000) (41 . 0.0000000000) (42 . 0.0000000000) (91 . 0) (10 1665.5800443922 62.7635991465) (40 . 0.0000000000) (41 . 0.0000000000) (42 . -0.2343570514) (91 . 0) (10 1665.1357332891 62.7635991463) (40 . 0.0000000000) (41 . 0.0000000000) (42 . 0.0000000000) (91 . 0) (10 1660.1800443838 62.2213902421) (40 . 0.0000000000) (41 . 0.0000000000) (42 . 0.5564744024) (91 . 0) (10 1659.4578888325 61.7734539620) (40 . 0.0000000000) (41 . 0.0000000000) (42 . 0.0000000000) (91 . 0) (10 1659.4578888325 61.8774783772) (40 . 0.0000000000) (41 . 0.0000000000) (42 . 0.2849552790) (91 . 0) (10 1659.5690266120 61.6983038651) (40 . 0.0000000000) (41 . 0.0000000000) (42 . 0.0000000000) (91 . 0) (10 1665.1357332886 58.9374763869) (40 . 0.0000000000) (41 . 0.0000000000) (42 . 0.2343570514) (91 . 0) (10 1665.5800443917 58.9374763871) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 65) (70 . 0) (43 . 0.0000000000) (38 . 0.0000000000) (39 . 0.0000000000) (10 1669.8578888324 67.1313221971) (40 . 0.0000000000) (41 . 0.0000000000) (42 . 0.0000000000) (91 . 0) (10 1669.8578888324 66.5967000000) (40 . 0.0000000000) (41 . 0.0000000000) (42 . 0.4142135624) (91 . 0) (10 1670.0578888326 66.3967000000) (40 . 0.0000000000) (41 . 0.0000000000) (42 . 0.0000000000) (91 . 0) (10 1671.0578888326 66.3967000000) (40 . 0.0000000000) (41 . 0.0000000000) (42 . -0.4142135624) (91 . 0) (10 1671.2578888323 66.1967000000) (40 . 0.0000000000) (41 . 0.0000000000) (42 . 0.0000000000) (91 . 0) (10 1671.2578888323 64.3779464253) (40 . 0.0000000000) (41 . 0.0000000000) (42 . -0.2849552787) (91 . 0) (10 1671.1467510530 64.1987719134) (40 . 0.0000000000) (41 . 0.0000000000) (42 . 0.0000000000) (91 . 0) (10 1665.5800443913 61.4379444351) (40 . 0.0000000000) (41 . 0.0000000000) (42 . -0.2343570514) (91 . 0) (10 1665.1357332882 61.4379444349) (40 . 0.0000000000) (41 . 0.0000000000) (42 . 0.0000000000) (91 . 0) (10 1659.5690266120 64.1987719129) (40 . 0.0000000000) (41 . 0.0000000000) (42 . -0.2849552790) (91 . 0) (10 1659.4578888325 64.3779464250) (40 . 0.0000000000) (41 . 0.0000000000) (42 . 0.0000000000) (91 . 0) (10 1659.4578888325 66.1967000000) (40 . 0.0000000000) (41 . 0.0000000000) (42 . -0.4142135624) (91 . 0) (10 1659.6578888327 66.3966999999) (40 . 0.0000000000) (41 . 0.0000000000) (42 . 0.0000000000) (91 . 0) (10 1660.6578888327 66.3966999999) (40 . 0.0000000000) (41 . 0.0000000000) (42 . 0.4142135624) (91 . 0) (10 1660.8578888324 66.5967000000) (40 . 0.0000000000) (41 . 0.0000000000) (42 . 0.0000000000) (91 . 0) (10 1660.8578888324 67.1189032619) (40 . 0.0000000000) (41 . 0.0000000000) (42 . 0.1876437528) (91 . 0) (10 1660.8053196605 67.2540481876) (40 . 0.0000000000) (41 . 0.0000000000) (42 . 0.0000000000) (91 . 0) (10 1659.8173393171 68.3318449257) (40 . 0.0000000000) (41 . 0.0000000000) (42 . 0.2102297862) (91 . 0) (10 1659.6699084893 68.3966999999) (40 . 0.0000000000) (41 . 0.0000000000) (42 . 0.0000000000) (91 . 0) (10 1658.0578888326 68.3966999999) (40 . 0.0000000000) (41 . 0.0000000000) (42 . 0.4142135624) (91 . 0) (10 1657.8578888324 68.1967000000) (40 . 0.0000000000) (41 . 0.0000000000) (42 . 0.0000000000) (91 . 0) (10 1657.8578888324 56.5967000000) (40 . 0.0000000000) (41 . 0.0000000000) (42 . 0.4142135624) (91 . 0) (10 1658.0578888326 56.3966999999) (40 . 0.0000000000) (41 . 0.0000000000) (42 . 0.0000000000) (91 . 0) (10 1659.0578888326 56.3966999999) (40 . 0.0000000000) (41 . 0.0000000000) (42 . 0.4142135624) (91 . 0) (10 1659.2578888323 56.5967000000) (40 . 0.0000000000) (41 . 0.0000000000) (42 . 0.0000000000) (91 . 0) (10 1659.2578888323 59.0967000000) (40 . 0.0000000000) (41 . 0.0000000000) (42 . -0.5788431251) (91 . 0) (10 1660.0098243451 59.5285894504) (40 . 0.0000000000) (41 . 0.0000000000) (42 . 0.0000000000) (91 . 0) (10 1660.5800443843 59.2457868447) (40 . 0.0000000000) (41 . 0.0000000000) (42 . -0.2849552788) (91 . 0) (10 1660.8578888324 58.7978505647) (40 . 0.0000000000) (41 . 0.0000000000) (42 . 0.0000000000) (91 . 0) (10 1660.8578888324 54.3533563146) (40 . 0.0000000000) (41 . 0.0000000000) (42 . -0.2840790438) (91 . 0) (10 1660.7473315515 54.1744708764) (40 . 0.0000000000) (41 . 0.0000000000) (42 . 0.0000000000) (91 . 0) (10 1660.5684461134 54.0850281572) (40 . 0.0000000000) (41 . 0.0000000000) (42 . 0.4142135624) (91 . 0) (10 1660.4790033942 53.8167000000) (40 . 0.0000000000) (41 . 0.0000000000) (42 . 0.0000000000) (91 . 0) (10 1661.0837247542 52.6072572809) (40 . 0.0000000000) (41 . 0.0000000000) (42 . 0.2840790438) (91 . 0) (10 1661.2626101922 52.4967000000) (40 . 0.0000000000) (41 . 0.0000000000) (42 . 0.0000000000) (91 . 0) (10 1661.9390033942 52.4967000000) (40 . 0.0000000000) (41 . 0.0000000000) (42 . 0.4142135624) (91 . 0) (10 1662.1390033944 52.6967000000) (40 . 0.0000000000) (41 . 0.0000000000) (42 . 0.0000000000) (91 . 0) (10 1662.1390033944 57.9432778508) (40 . 0.0000000000) (41 . 0.0000000000) (42 . -0.5564744024) (91 . 0) (10 1662.8611589456 58.3912141310) (40 . 0.0000000000) (41 . 0.0000000000) (42 . 0.0000000000) (91 . 0) (10 1665.2690266205 57.1970238086) (40 . 0.0000000000) (41 . 0.0000000000) (42 . 0.2343570514) (91 . 0) (10 1665.4467510618 57.1970238087) (40 . 0.0000000000) (41 . 0.0000000000) (42 . 0.0000000000) (91 . 0) (10 1667.8546187187 58.3912141254) (40 . 0.0000000000) (41 . 0.0000000000) (42 . -0.5564744028) (91 . 0) (10 1668.5767742705 57.9432778455) (40 . 0.0000000000) (41 . 0.0000000000) (42 . 0.0000000000) (91 . 0) (10 1668.5767742705 52.6967000000) (40 . 0.0000000000) (41 . 0.0000000000) (42 . 0.4142135624) (91 . 0) (10 1668.7767742707 52.4967000000) (40 . 0.0000000000) (41 . 0.0000000000) (42 . 0.0000000000) (91 . 0) (10 1669.4531674732 52.4967000000) (40 . 0.0000000000) (41 . 0.0000000000) (42 . 0.2840790438) (91 . 0) (10 1669.6320529112 52.6072572809) (40 . 0.0000000000) (41 . 0.0000000000) (42 . 0.0000000000) (91 . 0) (10 1670.2367742706 53.8167000000) (40 . 0.0000000000) (41 . 0.0000000000) (42 . 0.4142135624) (91 . 0) (10 1670.1473315518 54.0850281573) (40 . 0.0000000000) (41 . 0.0000000000) (42 . 0.0000000000) (91 . 0) (10 1669.9684461134 54.1744708764) (40 . 0.0000000000) (41 . 0.0000000000) (42 . -0.2840790438) (91 . 0) (10 1669.8578888324 54.3533563146) (40 . 0.0000000000) (41 . 0.0000000000) (42 . 0.0000000000) (91 . 0) (10 1669.8578888324 58.7978505647) (40 . 0.0000000000) (41 . 0.0000000000) (42 . -0.2849552788) (91 . 0) (10 1670.1357332810 59.2457868447) (40 . 0.0000000000) (41 . 0.0000000000) (42 . 0.0000000000) (91 . 0) (10 1670.7059533197 59.5285894504) (40 . 0.0000000000) (41 . 0.0000000000) (42 . -0.5788431251) (91 . 0) (10 1671.4578888325 59.0967000000) (40 . 0.0000000000) (41 . 0.0000000000) (42 . 0.0000000000) (91 . 0) (10 1671.4578888325 56.5967000000) (40 . 0.0000000000) (41 . 0.0000000000) (42 . 0.4142135624) (91 . 0) (10 1671.6578888327 56.3967000000) (40 . 0.0000000000) (41 . 0.0000000000) (42 . 0.0000000000) (91 . 0) (10 1672.6578888327 56.3967000000) (40 . 0.0000000000) (41 . 0.0000000000) (42 . 0.4142135624) (91 . 0) (10 1672.8578888324 56.5967000000) (40 . 0.0000000000) (41 . 0.0000000000) (42 . 0.0000000000) (91 . 0) (10 1672.8578888324 68.1967000000) (40 . 0.0000000000) (41 . 0.0000000000) (42 . 0.4142135624) (91 . 0) (10 1672.6578888327 68.3967000000) (40 . 0.0000000000) (41 . 0.0000000000) (42 . 0.0000000000) (91 . 0) (10 1671.0454832283 68.3966999999) (40 . 0.0000000000) (41 . 0.0000000000) (42 . 0.2102297862) (91 . 0) (10 1670.8980524004 68.3318449257) (40 . 0.0000000000) (41 . 0.0000000000) (42 . 0.0000000000) (91 . 0) (10 1669.9100720570 67.2540481876) (40 . 0.0000000000) (41 . 0.0000000000) (42 . 0.1876437528) (91 . 0) (10 1669.8575028851 67.1189032619) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 80) (70 . 1) (43 . 0.0000000000) (38 . 0.0000000000) (39 . 0.0000000000) (10 1644.0578888402 72.8967000000) (40 . 0.0000000000) (41 . 0.0000000000) (42 . 0.4142135624) (91 . 0) (10 1643.5578888402 73.3967000000) (40 . 0.0000000000) (41 . 0.0000000000) (42 . 0.0000000000) (91 . 0) (10 1636.9578888402 73.3967000000) (40 . 0.0000000000) (41 . 0.0000000000) (42 . -0.4142135624) (91 . 0) (10 1636.4578888402 73.8967000000) (40 . 0.0000000000) (41 . 0.0000000000) (42 . 0.0000000000) (91 . 0) (10 1636.4578888402 77.8967000000) (40 . 0.0000000000) (41 . 0.0000000000) (42 . 0.4142135624) (91 . 0) (10 1635.9578888402 78.3967000000) (40 . 0.0000000000) (41 . 0.0000000000) (42 . 0.0000000000) (91 . 0) (10 1635.6594945468 78.3967000000) (40 . 0.0000000000) (41 . 0.0000000000) (42 . 0.3152987889) (91 . 0) (10 1635.1896482364 78.0677100716) (40 . 0.0000000000) (41 . 0.0000000000) (42 . 0.0000000000) (91 . 0) (10 1634.5699503160 76.3651040286) (40 . 0.0000000000) (41 . 0.0000000000) (42 . 0.5205670506) (91 . 0) (10 1634.7578888402 76.0967000000) (40 . 0.0000000000) (41 . 0.0000000000) (42 . 0.0000000000) (91 . 0) (10 1634.9578888402 76.0967000000) (40 . 0.0000000000) (41 . 0.0000000000) (42 . -0.4142135624) (91 . 0) (10 1635.2578888402 75.7967000000) (40 . 0.0000000000) (41 . 0.0000000000) (42 . 0.0000000000) (91 . 0) (10 1635.2578888402 73.8967000000) (40 . 0.0000000000) (41 . 0.0000000000) (42 . -0.4142135624) (91 . 0) (10 1634.7578888402 73.3967000000) (40 . 0.0000000000) (41 . 0.0000000000) (42 . 0.0000000000) (91 . 0) (10 1634.5578888402 73.3967000000) (40 . 0.0000000000) (41 . 0.0000000000) (42 . 0.4142135624) (91 . 0) (10 1634.0578888402 72.8967000000) (40 . 0.0000000000) (41 . 0.0000000000) (42 . 0.0000000000) (91 . 0) (10 1634.0578888402 68.8967000000) (40 . 0.0000000000) (41 . 0.0000000000) (42 . 0.4142135624) (91 . 0) (10 1634.5578888402 68.3967000000) (40 . 0.0000000000) (41 . 0.0000000000) (42 . 0.0000000000) (91 . 0) (10 1637.3578888402 68.3967000000) (40 . 0.0000000000) (41 . 0.0000000000) (42 . 0.4142135624) (91 . 0) (10 1637.8578888402 68.8967000000) (40 . 0.0000000000) (41 . 0.0000000000) (42 . 0.0000000000) (91 . 0) (10 1637.8578888402 69.0967000000) (40 . 0.0000000000) (41 . 0.0000000000) (42 . 0.4142135624) (91 . 0) (10 1637.3578888402 69.5967000000) (40 . 0.0000000000) (41 . 0.0000000000) (42 . 0.0000000000) (91 . 0) (10 1636.9578888402 69.5967000000) (40 . 0.0000000000) (41 . 0.0000000000) (42 . -0.4142135624) (91 . 0) (10 1636.4578888402 70.0967000000) (40 . 0.0000000000) (41 . 0.0000000000) (42 . 0.0000000000) (91 . 0) (10 1636.4578888402 70.7967000000) (40 . 0.0000000000) (41 . 0.0000000000) (42 . -0.4142135624) (91 . 0) (10 1636.9578888402 71.2967000000) (40 . 0.0000000000) (41 . 0.0000000000) (42 . 0.0000000000) (91 . 0) (10 1641.1578888402 71.2967000000) (40 . 0.0000000000) (41 . 0.0000000000) (42 . -0.4142135624) (91 . 0) (10 1641.6578888402 70.7967000000) (40 . 0.0000000000) (41 . 0.0000000000) (42 . 0.0000000000) (91 . 0) (10 1641.6578888402 70.0967000000) (40 . 0.0000000000) (41 . 0.0000000000) (42 . -0.4142135624) (91 . 0) (10 1641.1578888402 69.5967000000) (40 . 0.0000000000) (41 . 0.0000000000) (42 . 0.0000000000) (91 . 0) (10 1640.7578888402 69.5967000000) (40 . 0.0000000000) (41 . 0.0000000000) (42 . 0.4142135624) (91 . 0) (10 1640.2578888402 69.0967000000) (40 . 0.0000000000) (41 . 0.0000000000) (42 . 0.0000000000) (91 . 0) (10 1640.2578888402 68.8967000000) (40 . 0.0000000000) (41 . 0.0000000000) (42 . 0.4142135624) (91 . 0) (10 1640.7578888402 68.3967000000) (40 . 0.0000000000) (41 . 0.0000000000) (42 . 0.0000000000) (91 . 0) (10 1665.3578888402 68.3967000000) (40 . 0.0000000000) (41 . 0.0000000000) (42 . 0.0000000000) (91 . 0) (10 1689.9578888402 68.3967000000) (40 . 0.0000000000) (41 . 0.0000000000) (42 . 0.4142135624) (91 . 0) (10 1690.4578888402 68.8967000000) (40 . 0.0000000000) (41 . 0.0000000000) (42 . 0.0000000000) (91 . 0) (10 1690.4578888402 69.0967000000) (40 . 0.0000000000) (41 . 0.0000000000) (42 . 0.4142135624) (91 . 0) (10 1689.9578888402 69.5967000000) (40 . 0.0000000000) (41 . 0.0000000000) (42 . 0.0000000000) (91 . 0) (10 1689.5578888402 69.5967000000) (40 . 0.0000000000) (41 . 0.0000000000) (42 . -0.4142135624) (91 . 0) (10 1689.0578888402 70.0967000000) (40 . 0.0000000000) (41 . 0.0000000000) (42 . 0.0000000000) (91 . 0) (10 1689.0578888402 70.7967000000) (40 . 0.0000000000) (41 . 0.0000000000) (42 . -0.4142135624) (91 . 0) (10 1689.5578888402 71.2967000000) (40 . 0.0000000000) (41 . 0.0000000000) (42 . 0.0000000000) (91 . 0) (10 1693.7578888402 71.2967000000) (40 . 0.0000000000) (41 . 0.0000000000) (42 . -0.4142135624) (91 . 0) (10 1694.2578888402 70.7967000000) (40 . 0.0000000000) (41 . 0.0000000000) (42 . 0.0000000000) (91 . 0) (10 1694.2578888402 70.0967000000) (40 . 0.0000000000) (41 . 0.0000000000) (42 . -0.4142135624) (91 . 0) (10 1693.7578888402 69.5967000000) (40 . 0.0000000000) (41 . 0.0000000000) (42 . 0.0000000000) (91 . 0) (10 1693.3578888402 69.5967000000) (40 . 0.0000000000) (41 . 0.0000000000) (42 . 0.4142135624) (91 . 0) (10 1692.8578888402 69.0967000000) (40 . 0.0000000000) (41 . 0.0000000000) (42 . 0.0000000000) (91 . 0) (10 1692.8578888402 68.8967000000) (40 . 0.0000000000) (41 . 0.0000000000) (42 . 0.4142135624) (91 . 0) (10 1693.3578888402 68.3967000000) (40 . 0.0000000000) (41 . 0.0000000000) (42 . 0.0000000000) (91 . 0) (10 1696.1578888402 68.3967000000) (40 . 0.0000000000) (41 . 0.0000000000) (42 . 0.4142135624) (91 . 0) (10 1696.6578888402 68.8967000000) (40 . 0.0000000000) (41 . 0.0000000000) (42 . 0.0000000000) (91 . 0) (10 1696.6578888402 72.8967000000) (40 . 0.0000000000) (41 . 0.0000000000) (42 . 0.4142135624) (91 . 0) (10 1696.1578888402 73.3967000000) (40 . 0.0000000000) (41 . 0.0000000000) (42 . 0.0000000000) (91 . 0) (10 1695.9578888402 73.3967000000) (40 . 0.0000000000) (41 . 0.0000000000) (42 . -0.4142135624) (91 . 0) (10 1695.4578888402 73.8967000000) (40 . 0.0000000000) (41 . 0.0000000000) (42 . 0.0000000000) (91 . 0) (10 1695.4578888402 75.7967000000) (40 . 0.0000000000) (41 . 0.0000000000) (42 . -0.4142135624) (91 . 0) (10 1695.7578888402 76.0967000000) (40 . 0.0000000000) (41 . 0.0000000000) (42 . 0.0000000000) (91 . 0) (10 1695.9578888402 76.0967000000) (40 . 0.0000000000) (41 . 0.0000000000) (42 . 0.5205670506) (91 . 0) (10 1696.1458273643 76.3651040286) (40 . 0.0000000000) (41 . 0.0000000000) (42 . 0.0000000000) (91 . 0) (10 1695.5261294440 78.0677100716) (40 . 0.0000000000) (41 . 0.0000000000) (42 . 0.3152987889) (91 . 0) (10 1695.0562831336 78.3967000000) (40 . 0.0000000000) (41 . 0.0000000000) (42 . 0.0000000000) (91 . 0) (10 1694.7578888402 78.3967000000) (40 . 0.0000000000) (41 . 0.0000000000) (42 . 0.4142135624) (91 . 0) (10 1694.2578888402 77.8967000000) (40 . 0.0000000000) (41 . 0.0000000000) (42 . 0.0000000000) (91 . 0) (10 1694.2578888402 73.8967000000) (40 . 0.0000000000) (41 . 0.0000000000) (42 . -0.4142135624) (91 . 0) (10 1693.7578888402 73.3967000000) (40 . 0.0000000000) (41 . 0.0000000000) (42 . 0.0000000000) (91 . 0) (10 1687.1578888402 73.3967000000) (40 . 0.0000000000) (41 . 0.0000000000) (42 . 0.4142135624) (91 . 0) (10 1686.6578888402 72.8967000000) (40 . 0.0000000000) (41 . 0.0000000000) (42 . 0.0000000000) (91 . 0) (10 1686.6578888402 71.8967000000) (40 . 0.0000000000) (41 . 0.0000000000) (42 . -0.4142135624) (91 . 0) (10 1686.1578888402 71.3967000000) (40 . 0.0000000000) (41 . 0.0000000000) (42 . 0.0000000000) (91 . 0) (10 1666.0235742652 71.3967000000) (40 . 0.0000000000) (41 . 0.0000000000) (42 . 0.1989123674) (91 . 0) (10 1665.8821529089 71.3381213562) (40 . 0.0000000000) (41 . 0.0000000000) (42 . 0.0000000000) (91 . 0) (10 1665.4993101964 70.9552786438) (40 . 0.0000000000) (41 . 0.0000000000) (42 . -0.1989123674) (91 . 0) (10 1665.3578888402 70.8967000000) (40 . 0.0000000000) (41 . 0.0000000000) (42 . -0.1989123674) (91 . 0) (10 1665.2164674840 70.9552786438) (40 . 0.0000000000) (41 . 0.0000000000) (42 . 0.0000000000) (91 . 0) (10 1664.8336247715 71.3381213562) (40 . 0.0000000000) (41 . 0.0000000000) (42 . 0.1989123674) (91 . 0) (10 1664.6922034153 71.3967000000) (40 . 0.0000000000) (41 . 0.0000000000) (42 . 0.0000000000) (91 . 0) (10 1644.5578888402 71.3967000000) (40 . 0.0000000000) (41 . 0.0000000000) (42 . -0.4142135624) (91 . 0) (10 1644.0578888402 71.8967000000) (40 . 0.0000000000) (41 . 0.0000000000) (42 . 0.0000000000) (91 . 0) (210 0.0000000000 0.0000000000 1.0000000000))
((0 . "LWPOLYLINE") (100 . "AcDbEntity") (67 . 0) (8 . "A-Window") (62 . 3) (6 . "Continuous") (100 . "AcDbPolyline") (90 . 44) (70 . 1) (43 . 0.0000000000) (38 . 0.0000000000) (39 . 0.0000000000) (10 -1641.3578888394 70.2966877930) (40 . 0.0000000000) (41 . 0.0000000000) (42 . 0.0000000000) (91 . 0) (10 -1641.3578888394 70.0967122070) (40 . 0.0000000000) (41 . 0.0000000000) (42 . 0.4142225008) (91 . 0) (10 -1640.9578888396 69.6967000000) (40 . 0.0000000000) (41 . 0.0000000000) (42 . 0.0000000000) (91 . 0) (10 -1640.7578888396 69.6967000000) (40 . 0.0000000000) (41 . 0.0000000000) (42 . -0.4142135624) (91 . 0) (10 -1640.1578888396 69.0967000000) (40 . 0.0000000000) (41 . 0.0000000000) (42 . 0.0000000000) (91 . 0) (10 -1640.1578888396 68.8967000000) (40 . 0.0000000000) (41 . 0.0000000000) (42 . -0.2513806714) (91 . 0) (10 -1640.4262263606 68.3967000000) (40 . 0.0000000000) (41 . 0.0000000000) (42 . 0.0000000000) (91 . 0) (10 -1642.1580630642 68.3967000000) (40 . 0.0000000000) (41 . 0.0000000000) (42 . 0.4142135624) (91 . 0) (10 -1642.6580630642 67.8967000000) (40 . 0.0000000000) (41 . 0.0000000000) (42 . 0.0000000000) (91 . 0) (10 -1642.6580630642 63.2967000000) (40 . 0.0000000000) (41 . 0.0000000000) (42 . 0.4142135624) (91 . 0) (10 -1642.1580630642 62.7967000000) (40 . 0.0000000000) (41 . 0.0000000000) (42 . 0.0000000000) (91 . 0) (10 -1641.9478591082 62.7967000000) (40 . 0.0000000000) (41 . 0.0000000000) (42 . 0.0000000000) (91 . 0) (10 -1641.8031742128 63.1989988506) (40 . 0.0000000000) (41 . 0.0000000000) (42 . 0.0000000000) (91 . 0) (10 -1641.4459367998 63.1989988506) (40 . 0.0000000000) (41 . 0.0000000000) (42 . 0.0000000000) (91 . 0) (10 -1641.3061924415 62.7967000000) (40 . 0.0000000000) (41 . 0.0000000000) (42 . 0.0000000000) (91 . 0) (10 -1640.6645257748 62.7967000000) (40 . 0.0000000000) (41 . 0.0000000000) (42 . 0.0000000000) (91 . 0) (10 -1640.5198408794 63.1989988506) (40 . 0.0000000000) (41 . 0.0000000000) (42 . 0.0000000000) (91 . 0) (10 -1640.1626034664 63.1989988506) (40 . 0.0000000000) (41 . 0.0000000000) (42 . 0.0000000000) (91 . 0) (10 -1640.0228591082 62.7967000000) (40 . 0.0000000000) (41 . 0.0000000000) (42 . 0.0000000000) (91 . 0) (10 -1639.3811924415 62.7967000000) (40 . 0.0000000000) (41 . 0.0000000000) (42 . 0.0000000000) (91 . 0) (10 -1639.2365075461 63.1989988506) (40 . 0.0000000000) (41 . 0.0000000000) (42 . 0.0000000000) (91 . 0) (10 -1638.8792701331 63.1989988506) (40 . 0.0000000000) (41 . 0.0000000000) (42 . 0.0000000000) (91 . 0) (10 -1638.7395257749 62.7967000000) (40 . 0.0000000000) (41 . 0.0000000000) (42 . 0.0000000000) (91 . 0) (10 -1638.0978591082 62.7967000000) (40 . 0.0000000000) (41 . 0.0000000000) (42 . 0.0000000000) (91 . 0) (10 -1637.9531742128 63.1989988506) (40 . 0.0000000000) (41 . 0.0000000000) (42 . 0.0000000000) (91 . 0) (10 -1637.5959367998 63.1989988506) (40 . 0.0000000000) (41 . 0.0000000000) (42 . 0.0000000000) (91 . 0) (10 -1637.4561924415 62.7967000000) (40 . 0.0000000000) (41 . 0.0000000000) (42 . 0.0000000000) (91 . 0) (10 -1636.8145257749 62.7967000000) (40 . 0.0000000000) (41 . 0.0000000000) (42 . 0.0000000000) (91 . 0) (10 -1636.6698408794 63.1989988506) (40 . 0.0000000000) (41 . 0.0000000000) (42 . 0.0000000000) (91 . 0) (10 -1636.3126034664 63.1989988506) (40 . 0.0000000000) (41 . 0.0000000000) (42 . 0.0000000000) (91 . 0) (10 -1636.1728591082 62.7967000000) (40 . 0.0000000000) (41 . 0.0000000000) (42 . 0.0000000000) (91 . 0) (10 -1635.9580630642 62.7967000000) (40 . 0.0000000000) (41 . 0.0000000000) (42 . 0.4142135624) (91 . 0) (10 -1635.4580630642 63.2967000000) (40 . 0.0000000000) (41 . 0.0000000000) (42 . 0.0000000000) (91 . 0) (10 -1635.4580630642 67.8967000000) (40 . 0.0000000000) (41 . 0.0000000000) (42 . 0.4142135624) (91 . 0) (10 -1635.9580630642 68.3967000000) (40 . 0.0000000000) (41 . 0.0000000000) (42 . 0.0000000000) (91 . 0) (10 -1637.6895513186 68.3967000000) (40 . 0.0000000000) (41 . 0.0000000000) (42 . -0.2513806714) (91 . 0) (10 -1637.9578888396 68.8967000000) (40 . 0.0000000000) (41 . 0.0000000000) (42 . 0.0000000000) (91 . 0) (10 -1637.9578888396 69.0967000000) (40 . 0.0000000000) (41 . 0.0000000000) (42 . -0.4142135624) (91 . 0) (10 -1637.3578888396 69.6967000000) (40 . 0.0000000000) (41 . 0.0000000000) (42 . 0.0000000000) (91 . 0) (10 -1637.1578888396 69.6967000000) (40 . 0.0000000000) (41 . 0.0000000000) (42 . 0.4142135624) (91 . 0) (10 -1636.7578888396 70.0967000000) (40 . 0.0000000000) (41 . 0.0000000000) (42 . 0.0000000000) (91 . 0) (10 -1636.7578888396 70.2967000000) (40 . 0.0000000000) (41 . 0.0000000000) (42 . 0.4142135624) (91 . 0) (10 -1637.1578888396 70.6967000000) (40 . 0.0000000000) (41 . 0.0000000000) (42 . 0.0000000000) (91 . 0) (10 -1640.9578888396 70.6967000000) (40 . 0.0000000000) (41 . 0.0000000000) (42 . 0.4142225008) (91 . 0) (210 0.0000000000 0.0000000000 -1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 -1636.9030630642 67.3467000000) (40 . 0.0000000000) (41 . 0.0000000000) (42 . 0.0000000000) (91 . 0) (10 -1636.9030630642 64.2467000000) (40 . 0.0000000000) (41 . 0.0000000000) (42 . 0.0000000000) (91 . 0) (10 -1638.4030630642 64.2467000000) (40 . 0.0000000000) (41 . 0.0000000000) (42 . 0.0000000000) (91 . 0) (10 -1638.4030630642 67.3467000000) (40 . 0.0000000000) (41 . 0.0000000000) (42 . 0.0000000000) (91 . 0) (210 0.0000000000 0.0000000000 -1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 -1639.7530630642 67.3467000000) (40 . 0.0000000000) (41 . 0.0000000000) (42 . 0.0000000000) (91 . 0) (10 -1639.7530630642 64.2467000000) (40 . 0.0000000000) (41 . 0.0000000000) (42 . 0.0000000000) (91 . 0) (10 -1641.2530630642 64.2467000000) (40 . 0.0000000000) (41 . 0.0000000000) (42 . 0.0000000000) (91 . 0) (10 -1641.2530630642 67.3467000000) (40 . 0.0000000000) (41 . 0.0000000000) (42 . 0.0000000000) (91 . 0) (210 0.0000000000 0.0000000000 -1.0000000000))
((0 . "LWPOLYLINE") (100 . "AcDbEntity") (67 . 0) (8 . "A-Window") (62 . 151) (6 . "Continuous") (100 . "AcDbPolyline") (90 . 44) (70 . 1) (43 . 0.0000000000) (38 . 0.0000000000) (39 . 0.0000000000) (10 1696.6578888402 91.8967000000) (40 . 0.0000000000) (41 . 0.0000000000) (42 . 0.0000000000) (91 . 0) (10 1696.6578888402 80.7967000000) (40 . 0.0000000000) (41 . 0.0000000000) (42 . -0.4142135624) (91 . 0) (10 1696.1578888402 80.2967000000) (40 . 0.0000000000) (41 . 0.0000000000) (42 . 0.0000000000) (91 . 0) (10 1694.1578888402 80.2967000000) (40 . 0.0000000000) (41 . 0.0000000000) (42 . 0.4142135624) (91 . 0) (10 1693.6578888402 79.7967000000) (40 . 0.0000000000) (41 . 0.0000000000) (42 . 0.0000000000) (91 . 0) (10 1693.6578888402 79.5967000000) (40 . 0.0000000000) (41 . 0.0000000000) (42 . 0.4142135624) (91 . 0) (10 1694.1578888402 79.0967000000) (40 . 0.0000000000) (41 . 0.0000000000) (42 . 0.0000000000) (91 . 0) (10 1696.1578888402 79.0967000000) (40 . 0.0000000000) (41 . 0.0000000000) (42 . -0.4142135624) (91 . 0) (10 1696.6578888402 78.5967000000) (40 . 0.0000000000) (41 . 0.0000000000) (42 . 0.0000000000) (91 . 0) (10 1696.6578888402 76.2967000000) (40 . 0.0000000000) (41 . 0.0000000000) (42 . -0.4142135624) (91 . 0) (10 1696.4578888402 76.0967000000) (40 . 0.0000000000) (41 . 0.0000000000) (42 . 0.0000000000) (91 . 0) (10 1695.7757356342 76.0967000000) (40 . 0.0000000000) (41 . 0.0000000000) (42 . 0.5522631265) (91 . 0) (10 1695.5954310227 75.8101537865) (40 . 0.0000000000) (41 . 0.0000000000) (42 . 0.0000000000) (91 . 0) (10 1696.6381934517 73.6377320594) (40 . 0.0000000000) (41 . 0.0000000000) (42 . -0.1123491485) (91 . 0) (10 1696.6578888402 73.5511858458) (40 . 0.0000000000) (41 . 0.0000000000) (42 . 0.0000000000) (91 . 0) (10 1696.6578888402 67.1967000000) (40 . 0.0000000000) (41 . 0.0000000000) (42 . 0.4142135624) (91 . 0) (10 1697.2578888402 66.5967000000) (40 . 0.0000000000) (41 . 0.0000000000) (42 . 0.4142135624) (91 . 0) (10 1697.8578888402 67.1967000000) (40 . 0.0000000000) (41 . 0.0000000000) (42 . 0.0000000000) (91 . 0) (10 1697.8578888402 93.0967000000) (40 . 0.0000000000) (41 . 0.0000000000) (42 . 0.4142135624) (91 . 0) (10 1697.3578888402 93.5967000000) (40 . 0.0000000000) (41 . 0.0000000000) (42 . 0.0000000000) (91 . 0) (10 1665.3578888402 93.5967000000) (40 . 0.0000000000) (41 . 0.0000000000) (42 . 0.0000000000) (91 . 0) (10 1633.3578888402 93.5967000000) (40 . 0.0000000000) (41 . 0.0000000000) (42 . 0.4142135624) (91 . 0) (10 1632.8578888402 93.0967000000) (40 . 0.0000000000) (41 . 0.0000000000) (42 . 0.0000000000) (91 . 0) (10 1632.8578888402 67.1967000000) (40 . 0.0000000000) (41 . 0.0000000000) (42 . 0.4142135624) (91 . 0) (10 1633.4578888402 66.5967000000) (40 . 0.0000000000) (41 . 0.0000000000) (42 . 0.4142135624) (91 . 0) (10 1634.0578888402 67.1967000000) (40 . 0.0000000000) (41 . 0.0000000000) (42 . 0.0000000000) (91 . 0) (10 1634.0578888402 73.5511858458) (40 . 0.0000000000) (41 . 0.0000000000) (42 . -0.1123491485) (91 . 0) (10 1634.0775842287 73.6377320594) (40 . 0.0000000000) (41 . 0.0000000000) (42 . 0.0000000000) (91 . 0) (10 1635.1203466577 75.8101537865) (40 . 0.0000000000) (41 . 0.0000000000) (42 . 0.5522631265) (91 . 0) (10 1634.9400420462 76.0967000000) (40 . 0.0000000000) (41 . 0.0000000000) (42 . 0.0000000000) (91 . 0) (10 1634.2578888402 76.0967000000) (40 . 0.0000000000) (41 . 0.0000000000) (42 . -0.4142135624) (91 . 0) (10 1634.0578888402 76.2967000000) (40 . 0.0000000000) (41 . 0.0000000000) (42 . 0.0000000000) (91 . 0) (10 1634.0578888402 78.5967000000) (40 . 0.0000000000) (41 . 0.0000000000) (42 . -0.4142135624) (91 . 0) (10 1634.5578888402 79.0967000000) (40 . 0.0000000000) (41 . 0.0000000000) (42 . 0.0000000000) (91 . 0) (10 1636.5578888402 79.0967000000) (40 . 0.0000000000) (41 . 0.0000000000) (42 . 0.4142135624) (91 . 0) (10 1637.0578888402 79.5967000000) (40 . 0.0000000000) (41 . 0.0000000000) (42 . 0.0000000000) (91 . 0) (10 1637.0578888402 79.7967000000) (40 . 0.0000000000) (41 . 0.0000000000) (42 . 0.4142135624) (91 . 0) (10 1636.5578888402 80.2967000000) (40 . 0.0000000000) (41 . 0.0000000000) (42 . 0.0000000000) (91 . 0) (10 1634.5578888402 80.2967000000) (40 . 0.0000000000) (41 . 0.0000000000) (42 . -0.4142135624) (91 . 0) (10 1634.0578888402 80.7967000000) (40 . 0.0000000000) (41 . 0.0000000000) (42 . 0.0000000000) (91 . 0) (10 1634.0578888402 91.8967000000) (40 . 0.0000000000) (41 . 0.0000000000) (42 . -0.4142135624) (91 . 0) (10 1634.5578888402 92.3967000000) (40 . 0.0000000000) (41 . 0.0000000000) (42 . 0.0000000000) (91 . 0) (10 1665.3578888402 92.3967000000) (40 . 0.0000000000) (41 . 0.0000000000) (42 . 0.0000000000) (91 . 0) (10 1696.1578888402 92.3967000000) (40 . 0.0000000000) (41 . 0.0000000000) (42 . -0.4142135624) (91 . 0) (210 0.0000000000 0.0000000000 1.0000000000))
((0 . "LINE") (100 . "AcDbEntity") (67 . 0) (8 . "A-Window") (62 . 151) (6 . "Continuous") (100 . "AcDbLine") (10 1667.5828888399 59.8994120805 0.0000000000) (11 1667.5828888399 60.7929549452 0.0000000000) (210 0.0000000000 0.0000000000 1.0000000000))
((0 . "LINE") (100 . "AcDbEntity") (67 . 0) (8 . "A-Window") (62 . 151) (6 . "Continuous") (100 . "AcDbLine") (10 1667.5828888399 61.5694120805 0.0000000000) (11 1667.5828888399 62.4629549452 0.0000000000) (210 0.0000000000 0.0000000000 1.0000000000))
((0 . "LINE") (100 . "AcDbEntity") (67 . 0) (8 . "A-Window") (62 . 151) (6 . "Continuous") (100 . "AcDbLine") (10 1667.5828888399 56.5594120805 0.0000000000) (11 1667.5828888399 57.4529549452 0.0000000000) (210 0.0000000000 0.0000000000 1.0000000000))
((0 . "LINE") (100 . "AcDbEntity") (67 . 0) (8 . "A-Window") (62 . 151) (6 . "Continuous") (100 . "AcDbLine") (10 1667.5828888399 58.2294120805 0.0000000000) (11 1667.5828888399 59.1229549452 0.0000000000) (210 0.0000000000 0.0000000000 1.0000000000))
((0 . "LINE") (100 . "AcDbEntity") (67 . 0) (8 . "A-Window") (62 . 151) (6 . "Continuous") (100 . "AcDbLine") (10 1663.1328888399 55.5896136866 0.0000000000) (11 1663.1328888399 56.4831565513 0.0000000000) (210 0.0000000000 0.0000000000 1.0000000000))
((0 . "LINE") (100 . "AcDbEntity") (67 . 0) (8 . "A-Window") (62 . 151) (6 . "Continuous") (100 . "AcDbLine") (10 1663.1328888399 57.2596136866 0.0000000000) (11 1663.1328888399 58.1531565513 0.0000000000) (210 0.0000000000 0.0000000000 1.0000000000))
((0 . "LINE") (100 . "AcDbEntity") (67 . 0) (8 . "A-Window") (62 . 151) (6 . "Continuous") (100 . "AcDbLine") (10 1663.1328888399 58.9296136866 0.0000000000) (11 1663.1328888399 59.8231565513 0.0000000000) (210 0.0000000000 0.0000000000 1.0000000000))
((0 . "LINE") (100 . "AcDbEntity") (67 . 0) (8 . "A-Window") (62 . 151) (6 . "Continuous") (100 . "AcDbLine") (10 1663.1328888399 60.5996136866 0.0000000000) (11 1663.1328888399 61.4931565513 0.0000000000) (210 0.0000000000 0.0000000000 1.0000000000))
((0 . "LINE") (100 . "AcDbEntity") (67 . 0) (8 . "A-Window") (62 . 151) (6 . "Continuous") (100 . "AcDbLine") (10 1663.1328888399 62.2696136866 0.0000000000) (11 1663.1328888399 63.1631565513 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1663.1328888399 57.2596136866) (40 . 0.0000000000) (41 . 0.0000000000) (42 . 0.0000000000) (91 . 0) (10 1662.6078888399 56.8713851190) (40 . 0.0000000000) (41 . 0.0000000000) (42 . 0.0000000000) (91 . 0) (10 1663.1328888399 56.4831565513) (40 . 0.0000000000) (41 . 0.0000000000) (42 . 0.0000000000) (91 . 0) (10 1667.5828888399 57.4529549452) (40 . 0.0000000000) (41 . 0.0000000000) (42 . 0.0000000000) (91 . 0) (10 1668.1078888399 57.8411835129) (40 . 0.0000000000) (41 . 0.0000000000) (42 . 0.0000000000) (91 . 0) (10 1667.5828888399 58.2294120805) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1663.1328888399 60.5996136866) (40 . 0.0000000000) (41 . 0.0000000000) (42 . 0.0000000000) (91 . 0) (10 1662.6078888399 60.2113851190) (40 . 0.0000000000) (41 . 0.0000000000) (42 . 0.0000000000) (91 . 0) (10 1663.1328888399 59.8231565513) (40 . 0.0000000000) (41 . 0.0000000000) (42 . 0.0000000000) (91 . 0) (10 1667.5828888399 60.7929549452) (40 . 0.0000000000) (41 . 0.0000000000) (42 . 0.0000000000) (91 . 0) (10 1668.1078888399 61.1811835129) (40 . 0.0000000000) (41 . 0.0000000000) (42 . 0.0000000000) (91 . 0) (10 1667.5828888399 61.5694120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 1668.1078888399 59.5111835129 0.0000000000) (11 1662.6078888399 58.5413851190 0.0000000000) (210 0.0000000000 0.0000000000 1.0000000000))
((0 . "LINE") (100 . "AcDbEntity") (67 . 0) (8 . "A-Window") (62 . 151) (6 . "Continuous") (100 . "AcDbLine") (10 1668.1078888399 61.1811835129 0.0000000000) (11 1662.6078888399 60.2113851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1663.1328888399 58.9296136866) (40 . 0.0000000000) (41 . 0.0000000000) (42 . 0.0000000000) (91 . 0) (10 1662.6078888399 58.5413851190) (40 . 0.0000000000) (41 . 0.0000000000) (42 . 0.0000000000) (91 . 0) (10 1663.1328888399 58.1531565513) (40 . 0.0000000000) (41 . 0.0000000000) (42 . 0.0000000000) (91 . 0) (10 1667.5828888399 59.1229549452) (40 . 0.0000000000) (41 . 0.0000000000) (42 . 0.0000000000) (91 . 0) (10 1668.1078888399 59.5111835129) (40 . 0.0000000000) (41 . 0.0000000000) (42 . 0.0000000000) (91 . 0) (10 1667.5828888399 59.8994120805) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1663.1328888399 62.2696136866) (40 . 0.0000000000) (41 . 0.0000000000) (42 . 0.0000000000) (91 . 0) (10 1662.6078888399 61.8813851190) (40 . 0.0000000000) (41 . 0.0000000000) (42 . 0.0000000000) (91 . 0) (10 1663.1328888399 61.4931565513) (40 . 0.0000000000) (41 . 0.0000000000) (42 . 0.0000000000) (91 . 0) (10 1667.5828888399 62.4629549452) (40 . 0.0000000000) (41 . 0.0000000000) (42 . 0.0000000000) (91 . 0) (10 1668.1078888399 62.8511835129) (40 . 0.0000000000) (41 . 0.0000000000) (42 . 0.0000000000) (91 . 0) (10 1667.5828888399 63.2394120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 1668.1078888399 62.8511835129 0.0000000000) (11 1662.6078888399 61.8813851190 0.0000000000) (210 0.0000000000 0.0000000000 1.0000000000))
((0 . "LINE") (100 . "AcDbEntity") (67 . 0) (8 . "A-Window") (62 . 151) (6 . "Continuous") (100 . "AcDbLine") (10 1668.1078888399 57.8411835129 0.0000000000) (11 1662.6078888399 56.8713851190 0.0000000000) (210 0.0000000000 0.0000000000 1.0000000000))
((0 . "LINE") (100 . "AcDbEntity") (67 . 0) (8 . "A-Window") (62 . 151) (6 . "Continuous") (100 . "AcDbLine") (10 1667.5828888399 66.9194120805 0.0000000000) (11 1667.5828888399 67.8129549452 0.0000000000) (210 0.0000000000 0.0000000000 1.0000000000))
((0 . "LINE") (100 . "AcDbEntity") (67 . 0) (8 . "A-Window") (62 . 151) (6 . "Continuous") (100 . "AcDbLine") (10 1667.5828888399 61.9094120805 0.0000000000) (11 1667.5828888399 62.8029549452 0.0000000000) (210 0.0000000000 0.0000000000 1.0000000000))
((0 . "LINE") (100 . "AcDbEntity") (67 . 0) (8 . "A-Window") (62 . 151) (6 . "Continuous") (100 . "AcDbLine") (10 1667.5828888399 63.5794120805 0.0000000000) (11 1667.5828888399 64.4729549452 0.0000000000) (210 0.0000000000 0.0000000000 1.0000000000))
((0 . "LINE") (100 . "AcDbEntity") (67 . 0) (8 . "A-Window") (62 . 151) (6 . "Continuous") (100 . "AcDbLine") (10 1667.5828888399 65.2494120805 0.0000000000) (11 1667.5828888399 66.1429549452 0.0000000000) (210 0.0000000000 0.0000000000 1.0000000000))
((0 . "LINE") (100 . "AcDbEntity") (67 . 0) (8 . "A-Window") (62 . 151) (6 . "Continuous") (100 . "AcDbLine") (10 1667.5828888399 71.9294120805 0.0000000000) (11 1667.5828888399 72.8229549452 0.0000000000) (210 0.0000000000 0.0000000000 1.0000000000))
((0 . "LINE") (100 . "AcDbEntity") (67 . 0) (8 . "A-Window") (62 . 151) (6 . "Continuous") (100 . "AcDbLine") (10 1667.5828888399 70.2594120805 0.0000000000) (11 1667.5828888399 71.1529549452 0.0000000000) (210 0.0000000000 0.0000000000 1.0000000000))
((0 . "LINE") (100 . "AcDbEntity") (67 . 0) (8 . "A-Window") (62 . 151) (6 . "Continuous") (100 . "AcDbLine") (10 1667.5828888399 68.5894120805 0.0000000000) (11 1667.5828888399 69.4829549452 0.0000000000) (210 0.0000000000 0.0000000000 1.0000000000))
((0 . "LINE") (100 . "AcDbEntity") (67 . 0) (8 . "A-Window") (62 . 151) (6 . "Continuous") (100 . "AcDbLine") (10 1663.1328888399 60.9396136866 0.0000000000) (11 1663.1328888399 61.8331565513 0.0000000000) (210 0.0000000000 0.0000000000 1.0000000000))
((0 . "LINE") (100 . "AcDbEntity") (67 . 0) (8 . "A-Window") (62 . 151) (6 . "Continuous") (100 . "AcDbLine") (10 1663.1328888399 65.9496136866 0.0000000000) (11 1663.1328888399 66.8431565513 0.0000000000) (210 0.0000000000 0.0000000000 1.0000000000))
((0 . "LINE") (100 . "AcDbEntity") (67 . 0) (8 . "A-Window") (62 . 151) (6 . "Continuous") (100 . "AcDbLine") (10 1663.1328888399 67.6196136866 0.0000000000) (11 1663.1328888399 68.5131565513 0.0000000000) (210 0.0000000000 0.0000000000 1.0000000000))
((0 . "LINE") (100 . "AcDbEntity") (67 . 0) (8 . "A-Window") (62 . 151) (6 . "Continuous") (100 . "AcDbLine") (10 1663.1328888399 62.6096136866 0.0000000000) (11 1663.1328888399 63.5031565513 0.0000000000) (210 0.0000000000 0.0000000000 1.0000000000))
((0 . "LINE") (100 . "AcDbEntity") (67 . 0) (8 . "A-Window") (62 . 151) (6 . "Continuous") (100 . "AcDbLine") (10 1663.1328888399 64.2796136866 0.0000000000) (11 1663.1328888399 65.1731565513 0.0000000000) (210 0.0000000000 0.0000000000 1.0000000000))
((0 . "LINE") (100 . "AcDbEntity") (67 . 0) (8 . "A-Window") (62 . 151) (6 . "Continuous") (100 . "AcDbLine") (10 1663.1328888399 69.2896136866 0.0000000000) (11 1663.1328888399 70.1831565513 0.0000000000) (210 0.0000000000 0.0000000000 1.0000000000))
((0 . "LINE") (100 . "AcDbEntity") (67 . 0) (8 . "A-Window") (62 . 151) (6 . "Continuous") (100 . "AcDbLine") (10 1663.1328888399 70.9596136866 0.0000000000) (11 1663.1328888399 71.8531565513 0.0000000000) (210 0.0000000000 0.0000000000 1.0000000000))
((0 . "LINE") (100 . "AcDbEntity") (67 . 0) (8 . "A-Window") (62 . 151) (6 . "Continuous") (100 . "AcDbLine") (10 1663.1328888399 72.6296136866 0.0000000000) (11 1663.1328888399 72.8917774718 0.0000000000) (210 0.0000000000 0.0000000000 1.0000000000))
((0 . "LINE") (100 . "AcDbEntity") (67 . 0) (8 . "A-Window") (62 . 151) (6 . "Continuous") (100 . "AcDbLine") (10 1668.1078888399 63.1911835129 0.0000000000) (11 1662.6078888399 62.2213851189 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1663.1328888399 62.6096136866) (40 . 0.0000000000) (41 . 0.0000000000) (42 . 0.0000000000) (91 . 0) (10 1662.6078888399 62.2213851189) (40 . 0.0000000000) (41 . 0.0000000000) (42 . 0.0000000000) (91 . 0) (10 1663.1328888399 61.8331565513) (40 . 0.0000000000) (41 . 0.0000000000) (42 . 0.0000000000) (91 . 0) (10 1667.5828888399 62.8029549452) (40 . 0.0000000000) (41 . 0.0000000000) (42 . 0.0000000000) (91 . 0) (10 1668.1078888399 63.1911835129) (40 . 0.0000000000) (41 . 0.0000000000) (42 . 0.0000000000) (91 . 0) (10 1667.5828888399 63.5794120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 1668.1078888399 64.8611835129 0.0000000000) (11 1662.6078888399 63.8913851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1663.1328888399 64.2796136866) (40 . 0.0000000000) (41 . 0.0000000000) (42 . 0.0000000000) (91 . 0) (10 1662.6078888399 63.8913851190) (40 . 0.0000000000) (41 . 0.0000000000) (42 . 0.0000000000) (91 . 0) (10 1663.1328888399 63.5031565513) (40 . 0.0000000000) (41 . 0.0000000000) (42 . 0.0000000000) (91 . 0) (10 1667.5828888399 64.4729549452) (40 . 0.0000000000) (41 . 0.0000000000) (42 . 0.0000000000) (91 . 0) (10 1668.1078888399 64.8611835129) (40 . 0.0000000000) (41 . 0.0000000000) (42 . 0.0000000000) (91 . 0) (10 1667.5828888399 65.2494120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 1668.1078888399 66.5311835129 0.0000000000) (11 1662.6078888399 65.5613851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1663.1328888399 65.9496136866) (40 . 0.0000000000) (41 . 0.0000000000) (42 . 0.0000000000) (91 . 0) (10 1662.6078888399 65.5613851190) (40 . 0.0000000000) (41 . 0.0000000000) (42 . 0.0000000000) (91 . 0) (10 1663.1328888399 65.1731565513) (40 . 0.0000000000) (41 . 0.0000000000) (42 . 0.0000000000) (91 . 0) (10 1667.5828888399 66.1429549452) (40 . 0.0000000000) (41 . 0.0000000000) (42 . 0.0000000000) (91 . 0) (10 1668.1078888399 66.5311835129) (40 . 0.0000000000) (41 . 0.0000000000) (42 . 0.0000000000) (91 . 0) (10 1667.5828888399 66.9194120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 1668.1078888399 68.2011835129 0.0000000000) (11 1662.6078888399 67.2313851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1663.1328888399 67.6196136866) (40 . 0.0000000000) (41 . 0.0000000000) (42 . 0.0000000000) (91 . 0) (10 1662.6078888399 67.2313851190) (40 . 0.0000000000) (41 . 0.0000000000) (42 . 0.0000000000) (91 . 0) (10 1663.1328888399 66.8431565513) (40 . 0.0000000000) (41 . 0.0000000000) (42 . 0.0000000000) (91 . 0) (10 1667.5828888399 67.8129549452) (40 . 0.0000000000) (41 . 0.0000000000) (42 . 0.0000000000) (91 . 0) (10 1668.1078888399 68.2011835129) (40 . 0.0000000000) (41 . 0.0000000000) (42 . 0.0000000000) (91 . 0) (10 1667.5828888399 68.5894120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 1668.1078888399 69.8711835129 0.0000000000) (11 1662.6078888399 68.9013851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1663.1328888399 69.2896136866) (40 . 0.0000000000) (41 . 0.0000000000) (42 . 0.0000000000) (91 . 0) (10 1662.6078888399 68.9013851190) (40 . 0.0000000000) (41 . 0.0000000000) (42 . 0.0000000000) (91 . 0) (10 1663.1328888399 68.5131565513) (40 . 0.0000000000) (41 . 0.0000000000) (42 . 0.0000000000) (91 . 0) (10 1667.5828888399 69.4829549452) (40 . 0.0000000000) (41 . 0.0000000000) (42 . 0.0000000000) (91 . 0) (10 1668.1078888399 69.8711835129) (40 . 0.0000000000) (41 . 0.0000000000) (42 . 0.0000000000) (91 . 0) (10 1667.5828888399 70.2594120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 1668.1078888399 71.5411835129 0.0000000000) (11 1662.6078888399 70.5713851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1663.1328888399 70.9596136866) (40 . 0.0000000000) (41 . 0.0000000000) (42 . 0.0000000000) (91 . 0) (10 1662.6078888399 70.5713851190) (40 . 0.0000000000) (41 . 0.0000000000) (42 . 0.0000000000) (91 . 0) (10 1663.1328888399 70.1831565513) (40 . 0.0000000000) (41 . 0.0000000000) (42 . 0.0000000000) (91 . 0) (10 1667.5828888399 71.1529549452) (40 . 0.0000000000) (41 . 0.0000000000) (42 . 0.0000000000) (91 . 0) (10 1668.1078888399 71.5411835129) (40 . 0.0000000000) (41 . 0.0000000000) (42 . 0.0000000000) (91 . 0) (10 1667.5828888399 71.9294120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 1666.2964471660 72.8917774718 0.0000000000) (11 1662.6078888399 72.2413851190 0.0000000000) (210 0.0000000000 0.0000000000 1.0000000000))
((0 . "LWPOLYLINE") (100 . "AcDbEntity") (67 . 0) (8 . "A-Window") (62 . 151) (6 . "Continuous") (100 . "AcDbPolyline") (90 . 6) (70 . 0) (43 . 0.0000000000) (38 . 0.0000000000) (39 . 0.0000000000) (10 1664.3358490131 72.8917774718) (40 . 0.0000000000) (41 . 0.0000000000) (42 . 0.0000000000) (91 . 0) (10 1663.1328888399 72.6296136866) (40 . 0.0000000000) (41 . 0.0000000000) (42 . 0.0000000000) (91 . 0) (10 1662.6078888399 72.2413851190) (40 . 0.0000000000) (41 . 0.0000000000) (42 . 0.0000000000) (91 . 0) (10 1663.1328888399 71.8531565513) (40 . 0.0000000000) (41 . 0.0000000000) (42 . 0.0000000000) (91 . 0) (10 1667.5828888399 72.8229549452) (40 . 0.0000000000) (41 . 0.0000000000) (42 . 0.0000000000) (91 . 0) (10 1667.6759572781 72.8917774718) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 4) (70 . 1) (43 . 0.0000000000) (38 . 0.0000000000) (39 . 0.0000000000) (10 1670.8578888399 73.8917774718) (40 . 0.0000000000) (41 . 0.0000000000) (42 . 0.0000000000) (91 . 0) (10 1670.8578888399 72.8917774718) (40 . 0.0000000000) (41 . 0.0000000000) (42 . 0.0000000000) (91 . 0) (10 1659.8578888399 72.8917774718) (40 . 0.0000000000) (41 . 0.0000000000) (42 . 0.0000000000) (91 . 0) (10 1659.8578888399 73.8917774718) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 1668.1078888399 61.5211835128 0.0000000000) (11 1662.6078888399 63.5513851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1663.1328888399 60.9396136866) (40 . 0.0000000000) (41 . 0.0000000000) (42 . 0.0000000000) (91 . 0) (10 1662.6078888399 63.5513851190) (40 . 0.0000000000) (41 . 0.0000000000) (42 . 0.0000000000) (91 . 0) (10 1663.1328888399 63.1631565513) (40 . 0.0000000000) (41 . 0.0000000000) (42 . 0.0000000000) (91 . 0) (10 1667.5828888399 61.1329549452) (40 . 0.0000000000) (41 . 0.0000000000) (42 . 0.0000000000) (91 . 0) (10 1668.1078888399 61.5211835128) (40 . 0.0000000000) (41 . 0.0000000000) (42 . 0.0000000000) (91 . 0) (10 1667.5828888399 61.9094120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 1667.5828888399 63.2394120805 0.0000000000) (11 1667.5828888399 61.1329549452 0.0000000000) (210 0.0000000000 0.0000000000 1.0000000000))
((0 . "LINE") (100 . "AcDbEntity") (67 . 0) (8 . "A-Window") (62 . 151) (6 . "Continuous") (100 . "AcDbLine") (10 1668.8219904550 78.2917774718 0.0000000000) (11 1661.8937872248 78.2917774718 0.0000000000) (210 0.0000000000 0.0000000000 1.0000000000))
((0 . "LINE") (100 . "AcDbEntity") (67 . 0) (8 . "A-Window") (62 . 151) (6 . "CENTER2") (100 . "AcDbLine") (10 1665.3578888399 37.5451762388 0.0000000000) (11 1665.3578888399 81.5869711621 0.0000000000) (210 0.0000000000 0.0000000000 1.0000000000))
((0 . "LINE") (100 . "AcDbEntity") (67 . 0) (8 . "A-Window") (62 . 151) (6 . "Continuous") (100 . "AcDbLine") (10 1667.6672899167 77.2917774718 0.0000000000) (11 1667.6672899167 73.8917774718 0.0000000000) (210 0.0000000000 0.0000000000 1.0000000000))
((0 . "LINE") (100 . "AcDbEntity") (67 . 0) (8 . "A-Window") (62 . 151) (6 . "Continuous") (100 . "AcDbLine") (10 1663.0484877631 77.2917774718 0.0000000000) (11 1663.0484877631 73.8917774718 0.0000000000) (210 0.0000000000 0.0000000000 1.0000000000))
((0 . "LWPOLYLINE") (100 . "AcDbEntity") (67 . 0) (8 . "A-Window") (62 . 151) (6 . "Continuous") (100 . "AcDbPolyline") (90 . 6) (70 . 0) (43 . 0.0000000000) (38 . 0.0000000000) (39 . 0.0000000000) (10 1660.7390866864 73.8917774718) (40 . 0.0000000000) (41 . 0.0000000000) (42 . 0.0000000000) (91 . 0) (10 1660.7390866864 77.2917774718) (40 . 0.0000000000) (41 . 0.0000000000) (42 . -0.8660254038) (91 . 0) (10 1663.0484877631 77.2917774718) (40 . 0.0000000000) (41 . 0.0000000000) (42 . -0.4330127019) (91 . 0) (10 1667.6672899167 77.2917774718) (40 . 0.0000000000) (41 . 0.0000000000) (42 . -0.8660254038) (91 . 0) (10 1669.9766909934 77.2917774718) (40 . 0.0000000000) (41 . 0.0000000000) (42 . 0.0000000000) (91 . 0) (10 1669.9766909934 73.8917774718) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 4) (70 . 1) (43 . 0.0000000000) (38 . 0.0000000000) (39 . 0.0000000000) (10 1667.5828888399 42.6957453328) (40 . 0.0000000000) (41 . 0.0000000000) (42 . 0.0000000000) (91 . 0) (10 1665.9713231016 42.5675818646) (40 . 0.0000000000) (41 . 0.0000000000) (42 . 0.0000000000) (91 . 0) (10 1667.5828888399 43.0839739004) (40 . 0.0000000000) (41 . 0.0000000000) (42 . 0.0000000000) (91 . 0) (10 1667.7903888399 42.8898596166) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 1667.7903888399 42.8898596166 0.0000000000) (11 1665.9713231016 42.5675818646 0.0000000000) (210 0.0000000000 0.0000000000 1.0000000000))
((0 . "LINE") (100 . "AcDbEntity") (67 . 0) (8 . "A-Window") (62 . 151) (6 . "Continuous") (100 . "AcDbLine") (10 1667.5828888399 48.2094120805 0.0000000000) (11 1667.5828888399 49.1029549452 0.0000000000) (210 0.0000000000 0.0000000000 1.0000000000))
((0 . "LINE") (100 . "AcDbEntity") (67 . 0) (8 . "A-Window") (62 . 151) (6 . "Continuous") (100 . "AcDbLine") (10 1667.5828888399 56.5594120805 0.0000000000) (11 1667.5828888399 57.4529549452 0.0000000000) (210 0.0000000000 0.0000000000 1.0000000000))
((0 . "LINE") (100 . "AcDbEntity") (67 . 0) (8 . "A-Window") (62 . 151) (6 . "Continuous") (100 . "AcDbLine") (10 1667.8941388399 44.5782406548 0.0000000000) (11 1666.6210499786 44.3526917877 0.0000000000) (210 0.0000000000 0.0000000000 1.0000000000))
((0 . "LINE") (100 . "AcDbEntity") (67 . 0) (8 . "A-Window") (62 . 151) (6 . "Continuous") (100 . "AcDbLine") (10 1667.5828888399 44.8694120805 0.0000000000) (11 1667.5828888399 45.7629549452 0.0000000000) (210 0.0000000000 0.0000000000 1.0000000000))
((0 . "LWPOLYLINE") (100 . "AcDbEntity") (67 . 0) (8 . "A-Window") (62 . 151) (6 . "Continuous") (100 . "AcDbPolyline") (90 . 5) (70 . 0) (43 . 0.0000000000) (38 . 0.0000000000) (39 . 0.0000000000) (10 1666.5110249297 44.0504004504) (40 . 0.0000000000) (41 . 0.0000000000) (42 . 0.0000000000) (91 . 0) (10 1667.5828888399 44.2870692290) (40 . 0.0000000000) (41 . 0.0000000000) (42 . 0.0000000000) (91 . 0) (10 1667.8941388399 44.5782406548) (40 . 0.0000000000) (41 . 0.0000000000) (42 . 0.0000000000) (91 . 0) (10 1667.5828888399 44.8694120805) (40 . 0.0000000000) (41 . 0.0000000000) (42 . 0.0000000000) (91 . 0) (10 1666.7415027544 44.6836330695) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 1667.5828888399 46.5394120805 0.0000000000) (11 1667.5828888399 47.4329549452 0.0000000000) (210 0.0000000000 0.0000000000 1.0000000000))
((0 . "LINE") (100 . "AcDbEntity") (67 . 0) (8 . "A-Window") (62 . 151) (6 . "Continuous") (100 . "AcDbLine") (10 1667.5828888399 43.0839739004 0.0000000000) (11 1667.5828888399 44.2870692290 0.0000000000) (210 0.0000000000 0.0000000000 1.0000000000))
((0 . "LINE") (100 . "AcDbEntity") (67 . 0) (8 . "A-Window") (62 . 151) (6 . "Continuous") (100 . "AcDbLine") (10 1663.1328888399 44.1620742983 0.0000000000) (11 1663.1328888399 44.7931565513 0.0000000000) (210 0.0000000000 0.0000000000 1.0000000000))
((0 . "LINE") (100 . "AcDbEntity") (67 . 0) (8 . "A-Window") (62 . 151) (6 . "Continuous") (100 . "AcDbLine") (10 1663.1328888399 45.5696136866 0.0000000000) (11 1663.1328888399 46.4631565513 0.0000000000) (210 0.0000000000 0.0000000000 1.0000000000))
((0 . "LINE") (100 . "AcDbEntity") (67 . 0) (8 . "A-Window") (62 . 151) (6 . "Continuous") (100 . "AcDbLine") (10 1663.1328888399 47.2396136866 0.0000000000) (11 1663.1328888399 48.1331565513 0.0000000000) (210 0.0000000000 0.0000000000 1.0000000000))
((0 . "LINE") (100 . "AcDbEntity") (67 . 0) (8 . "A-Window") (62 . 151) (6 . "Continuous") (100 . "AcDbLine") (10 1663.1328888399 57.2596136866 0.0000000000) (11 1663.1328888399 58.1531565513 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1663.1328888399 45.5696136866) (40 . 0.0000000000) (41 . 0.0000000000) (42 . 0.0000000000) (91 . 0) (10 1662.6078888399 45.1813851190) (40 . 0.0000000000) (41 . 0.0000000000) (42 . 0.0000000000) (91 . 0) (10 1663.1328888399 44.7931565513) (40 . 0.0000000000) (41 . 0.0000000000) (42 . 0.0000000000) (91 . 0) (10 1667.5828888399 45.7629549452) (40 . 0.0000000000) (41 . 0.0000000000) (42 . 0.0000000000) (91 . 0) (10 1668.1078888399 46.1511835129) (40 . 0.0000000000) (41 . 0.0000000000) (42 . 0.0000000000) (91 . 0) (10 1667.5828888399 46.5394120805) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1663.1328888399 55.5896136866) (40 . 0.0000000000) (41 . 0.0000000000) (42 . 0.0000000000) (91 . 0) (10 1662.6078888399 55.2013851190) (40 . 0.0000000000) (41 . 0.0000000000) (42 . 0.0000000000) (91 . 0) (10 1663.1328888399 54.8131565513) (40 . 0.0000000000) (41 . 0.0000000000) (42 . 0.0000000000) (91 . 0) (10 1667.5828888399 55.7829549452) (40 . 0.0000000000) (41 . 0.0000000000) (42 . 0.0000000000) (91 . 0) (10 1668.1078888399 56.1711835129) (40 . 0.0000000000) (41 . 0.0000000000) (42 . 0.0000000000) (91 . 0) (10 1667.5828888399 56.5594120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 1668.1078888399 47.8211835129 0.0000000000) (11 1662.6078888399 46.8513851190 0.0000000000) (210 0.0000000000 0.0000000000 1.0000000000))
((0 . "LINE") (100 . "AcDbEntity") (67 . 0) (8 . "A-Window") (62 . 151) (6 . "Continuous") (100 . "AcDbLine") (10 1668.1078888399 56.1711835129 0.0000000000) (11 1662.6078888399 55.2013851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1663.1328888399 47.2396136866) (40 . 0.0000000000) (41 . 0.0000000000) (42 . 0.0000000000) (91 . 0) (10 1662.6078888399 46.8513851190) (40 . 0.0000000000) (41 . 0.0000000000) (42 . 0.0000000000) (91 . 0) (10 1663.1328888399 46.4631565513) (40 . 0.0000000000) (41 . 0.0000000000) (42 . 0.0000000000) (91 . 0) (10 1667.5828888399 47.4329549452) (40 . 0.0000000000) (41 . 0.0000000000) (42 . 0.0000000000) (91 . 0) (10 1668.1078888399 47.8211835129) (40 . 0.0000000000) (41 . 0.0000000000) (42 . 0.0000000000) (91 . 0) (10 1667.5828888399 48.2094120805) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1663.1328888399 57.2596136866) (40 . 0.0000000000) (41 . 0.0000000000) (42 . 0.0000000000) (91 . 0) (10 1662.6078888399 56.8713851190) (40 . 0.0000000000) (41 . 0.0000000000) (42 . 0.0000000000) (91 . 0) (10 1663.1328888399 56.4831565513) (40 . 0.0000000000) (41 . 0.0000000000) (42 . 0.0000000000) (91 . 0) (10 1667.5828888399 57.4529549452) (40 . 0.0000000000) (41 . 0.0000000000) (42 . 0.0000000000) (91 . 0) (10 1668.1078888399 57.8411835129) (40 . 0.0000000000) (41 . 0.0000000000) (42 . 0.0000000000) (91 . 0) (10 1667.5828888399 58.2294120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 1668.1078888399 57.8411835129 0.0000000000) (11 1662.6078888399 56.8713851190 0.0000000000) (210 0.0000000000 0.0000000000 1.0000000000))
((0 . "LINE") (100 . "AcDbEntity") (67 . 0) (8 . "A-Window") (62 . 151) (6 . "Continuous") (100 . "AcDbLine") (10 1668.1078888399 46.1511835129 0.0000000000) (11 1662.6078888399 45.1813851190 0.0000000000) (210 0.0000000000 0.0000000000 1.0000000000))
((0 . "LWPOLYLINE") (100 . "AcDbEntity") (67 . 0) (8 . "A-Window") (62 . 151) (6 . "Continuous") (100 . "AcDbPolyline") (90 . 10) (70 . 0) (43 . 0.0000000000) (38 . 0.0000000000) (39 . 0.0000000000) (10 1667.5828888399 42.6957453328) (40 . 0.0000000000) (41 . 0.0000000000) (42 . 0.0000000000) (91 . 0) (10 1667.5828888399 41.0687741511) (40 . 0.0000000000) (41 . 0.0000000000) (42 . 0.0000000000) (91 . 0) (10 1665.3578888399 39.2017774718) (40 . 0.0000000000) (41 . 0.0000000000) (42 . 0.0000000000) (91 . 0) (10 1663.1328888399 41.0687741511) (40 . 0.0000000000) (41 . 0.0000000000) (42 . 0.0000000000) (91 . 0) (10 1663.1328888399 43.5797314468) (40 . 0.0000000000) (41 . 0.0000000000) (42 . 0.0000000000) (91 . 0) (10 1662.8216388399 43.8709028725) (40 . 0.0000000000) (41 . 0.0000000000) (42 . 0.0000000000) (91 . 0) (10 1663.1328888399 44.1620742983) (40 . 0.0000000000) (41 . 0.0000000000) (42 . -0.2138820884) (91 . 0) (10 1666.7415027544 44.6836330695) (40 . 0.0000000000) (41 . 0.0000000000) (42 . 0.0000000000) (91 . 0) (10 1664.8893620003 39.5949181700) (40 . 0.0000000000) (41 . 0.0000000000) (42 . -0.2315249815) (91 . 0) (10 1667.5828888399 41.0687741511) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 1667.5828888399 59.8994120805 0.0000000000) (11 1667.5828888399 60.7929549452 0.0000000000) (210 0.0000000000 0.0000000000 1.0000000000))
((0 . "LINE") (100 . "AcDbEntity") (67 . 0) (8 . "A-Window") (62 . 151) (6 . "Continuous") (100 . "AcDbLine") (10 1667.5828888399 61.5694120805 0.0000000000) (11 1667.5828888399 62.4629549452 0.0000000000) (210 0.0000000000 0.0000000000 1.0000000000))
((0 . "LINE") (100 . "AcDbEntity") (67 . 0) (8 . "A-Window") (62 . 151) (6 . "Continuous") (100 . "AcDbLine") (10 1667.5828888399 63.2394120805 0.0000000000) (11 1667.5828888399 61.1329549452 0.0000000000) (210 0.0000000000 0.0000000000 1.0000000000))
((0 . "LINE") (100 . "AcDbEntity") (67 . 0) (8 . "A-Window") (62 . 151) (6 . "Continuous") (100 . "AcDbLine") (10 1663.1328888399 58.9296136866 0.0000000000) (11 1663.1328888399 59.8231565513 0.0000000000) (210 0.0000000000 0.0000000000 1.0000000000))
((0 . "LINE") (100 . "AcDbEntity") (67 . 0) (8 . "A-Window") (62 . 151) (6 . "Continuous") (100 . "AcDbLine") (10 1663.1328888399 60.5996136866 0.0000000000) (11 1663.1328888399 61.4931565513 0.0000000000) (210 0.0000000000 0.0000000000 1.0000000000))
((0 . "LINE") (100 . "AcDbEntity") (67 . 0) (8 . "A-Window") (62 . 151) (6 . "Continuous") (100 . "AcDbLine") (10 1663.1328888399 62.2696136866 0.0000000000) (11 1663.1328888399 63.1631565513 0.0000000000) (210 0.0000000000 0.0000000000 1.0000000000))
((0 . "LINE") (100 . "AcDbEntity") (67 . 0) (8 . "A-Window") (62 . 151) (6 . "Continuous") (100 . "AcDbLine") (10 1668.1078888399 61.1811835129 0.0000000000) (11 1662.6078888399 60.2113851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1663.1328888399 60.5996136866) (40 . 0.0000000000) (41 . 0.0000000000) (42 . 0.0000000000) (91 . 0) (10 1662.6078888399 60.2113851190) (40 . 0.0000000000) (41 . 0.0000000000) (42 . 0.0000000000) (91 . 0) (10 1663.1328888399 59.8231565513) (40 . 0.0000000000) (41 . 0.0000000000) (42 . 0.0000000000) (91 . 0) (10 1667.5828888399 60.7929549452) (40 . 0.0000000000) (41 . 0.0000000000) (42 . 0.0000000000) (91 . 0) (10 1668.1078888399 61.1811835129) (40 . 0.0000000000) (41 . 0.0000000000) (42 . 0.0000000000) (91 . 0) (10 1667.5828888399 61.5694120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 1668.1078888399 62.8511835129 0.0000000000) (11 1662.6078888399 61.8813851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1663.1328888399 62.2696136866) (40 . 0.0000000000) (41 . 0.0000000000) (42 . 0.0000000000) (91 . 0) (10 1662.6078888399 61.8813851190) (40 . 0.0000000000) (41 . 0.0000000000) (42 . 0.0000000000) (91 . 0) (10 1663.1328888399 61.4931565513) (40 . 0.0000000000) (41 . 0.0000000000) (42 . 0.0000000000) (91 . 0) (10 1667.5828888399 62.4629549452) (40 . 0.0000000000) (41 . 0.0000000000) (42 . 0.0000000000) (91 . 0) (10 1668.1078888399 62.8511835129) (40 . 0.0000000000) (41 . 0.0000000000) (42 . 0.0000000000) (91 . 0) (10 1667.5828888399 63.2394120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 1668.1078888399 61.5211835128 0.0000000000) (11 1662.6078888399 63.5513851190 0.0000000000) (210 0.0000000000 0.0000000000 1.0000000000))
((0 . "LINE") (100 . "AcDbEntity") (67 . 0) (8 . "A-Window") (62 . 151) (6 . "Continuous") (100 . "AcDbLine") (10 1668.1078888399 59.5111835129 0.0000000000) (11 1662.6078888399 58.5413851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1663.1328888399 58.9296136866) (40 . 0.0000000000) (41 . 0.0000000000) (42 . 0.0000000000) (91 . 0) (10 1662.6078888399 58.5413851190) (40 . 0.0000000000) (41 . 0.0000000000) (42 . 0.0000000000) (91 . 0) (10 1663.1328888399 58.1531565513) (40 . 0.0000000000) (41 . 0.0000000000) (42 . 0.0000000000) (91 . 0) (10 1667.5828888399 59.1229549452) (40 . 0.0000000000) (41 . 0.0000000000) (42 . 0.0000000000) (91 . 0) (10 1668.1078888399 59.5111835129) (40 . 0.0000000000) (41 . 0.0000000000) (42 . 0.0000000000) (91 . 0) (10 1667.5828888399 59.8994120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 1667.5828888399 58.2294120805 0.0000000000) (11 1667.5828888399 59.1229549452 0.0000000000) (210 0.0000000000 0.0000000000 1.0000000000))
((0 . "LINE") (100 . "AcDbEntity") (67 . 0) (8 . "A-Window") (62 . 151) (6 . "Continuous") (100 . "AcDbLine") (10 1667.5828888399 54.8894120805 0.0000000000) (11 1667.5828888399 55.7829549452 0.0000000000) (210 0.0000000000 0.0000000000 1.0000000000))
((0 . "LINE") (100 . "AcDbEntity") (67 . 0) (8 . "A-Window") (62 . 151) (6 . "Continuous") (100 . "AcDbLine") (10 1663.1328888399 53.9196136866 0.0000000000) (11 1663.1328888399 54.8131565513 0.0000000000) (210 0.0000000000 0.0000000000 1.0000000000))
((0 . "LINE") (100 . "AcDbEntity") (67 . 0) (8 . "A-Window") (62 . 151) (6 . "Continuous") (100 . "AcDbLine") (10 1667.5828888399 54.8894120805 0.0000000000) (11 1667.5828888399 55.7829549452 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1663.1328888399 53.9196136866) (40 . 0.0000000000) (41 . 0.0000000000) (42 . 0.0000000000) (91 . 0) (10 1662.6078888399 53.5313851190) (40 . 0.0000000000) (41 . 0.0000000000) (42 . 0.0000000000) (91 . 0) (10 1663.1328888399 53.1431565513) (40 . 0.0000000000) (41 . 0.0000000000) (42 . 0.0000000000) (91 . 0) (10 1667.5828888399 54.1129549452) (40 . 0.0000000000) (41 . 0.0000000000) (42 . 0.0000000000) (91 . 0) (10 1668.1078888399 54.5011835129) (40 . 0.0000000000) (41 . 0.0000000000) (42 . 0.0000000000) (91 . 0) (10 1667.5828888399 54.8894120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 1668.1078888399 54.5011835129 0.0000000000) (11 1662.6078888399 53.5313851190 0.0000000000) (210 0.0000000000 0.0000000000 1.0000000000))
((0 . "LINE") (100 . "AcDbEntity") (67 . 0) (8 . "A-Window") (62 . 151) (6 . "Continuous") (100 . "AcDbLine") (10 1667.5828888399 53.2194120805 0.0000000000) (11 1667.5828888399 54.1129549452 0.0000000000) (210 0.0000000000 0.0000000000 1.0000000000))
((0 . "LINE") (100 . "AcDbEntity") (67 . 0) (8 . "A-Window") (62 . 151) (6 . "Continuous") (100 . "AcDbLine") (10 1663.1328888399 52.2496136866 0.0000000000) (11 1663.1328888399 53.1431565513 0.0000000000) (210 0.0000000000 0.0000000000 1.0000000000))
((0 . "LINE") (100 . "AcDbEntity") (67 . 0) (8 . "A-Window") (62 . 151) (6 . "Continuous") (100 . "AcDbLine") (10 1667.5828888399 53.2194120805 0.0000000000) (11 1667.5828888399 54.1129549452 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1663.1328888399 52.2496136866) (40 . 0.0000000000) (41 . 0.0000000000) (42 . 0.0000000000) (91 . 0) (10 1662.6078888399 51.8613851189) (40 . 0.0000000000) (41 . 0.0000000000) (42 . 0.0000000000) (91 . 0) (10 1663.1328888399 51.4731565513) (40 . 0.0000000000) (41 . 0.0000000000) (42 . 0.0000000000) (91 . 0) (10 1667.5828888399 52.4429549452) (40 . 0.0000000000) (41 . 0.0000000000) (42 . 0.0000000000) (91 . 0) (10 1668.1078888399 52.8311835129) (40 . 0.0000000000) (41 . 0.0000000000) (42 . 0.0000000000) (91 . 0) (10 1667.5828888399 53.2194120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 1668.1078888399 52.8311835129 0.0000000000) (11 1662.6078888399 51.8613851189 0.0000000000) (210 0.0000000000 0.0000000000 1.0000000000))
((0 . "LINE") (100 . "AcDbEntity") (67 . 0) (8 . "A-Window") (62 . 151) (6 . "Continuous") (100 . "AcDbLine") (10 1672.3578888399 71.3967000000 0.0000000000) (11 1673.8578888399 71.3967000000 0.0000000000) (210 0.0000000000 0.0000000000 1.0000000000))
((0 . "LINE") (100 . "AcDbEntity") (67 . 0) (8 . "A-Window") (62 . 151) (6 . "Continuous") (100 . "AcDbLine") (10 1672.3578888399 72.8917774718 0.0000000000) (11 1672.3578888399 71.3967000000 0.0000000000) (210 0.0000000000 0.0000000000 1.0000000000))
((0 . "LINE") (100 . "AcDbEntity") (67 . 0) (8 . "A-Window") (62 . 151) (6 . "Continuous") (100 . "AcDbLine") (10 1670.8177271265 72.8917774718 0.0000000000) (11 1672.3578888399 72.8917774718 0.0000000000) (210 0.0000000000 0.0000000000 1.0000000000))
((0 . "LINE") (100 . "AcDbEntity") (67 . 0) (8 . "A-Window") (62 . 151) (6 . "Continuous") (100 . "AcDbLine") (10 1658.3578888399 71.3967000000 0.0000000000) (11 1658.3578888399 72.8917774718 0.0000000000) (210 0.0000000000 0.0000000000 1.0000000000))
((0 . "LINE") (100 . "AcDbEntity") (67 . 0) (8 . "A-Window") (62 . 151) (6 . "Continuous") (100 . "AcDbLine") (10 1656.8578888399 71.3967000000 0.0000000000) (11 1658.3578888399 71.3967000000 0.0000000000) (210 0.0000000000 0.0000000000 1.0000000000))
((0 . "LWPOLYLINE") (100 . "AcDbEntity") (67 . 0) (8 . "A-Window") (62 . 151) (6 . "Continuous") (100 . "AcDbPolyline") (90 . 4) (70 . 1) (43 . 0.0000000000) (38 . 0.0000000000) (39 . 0.0000000000) (10 1672.3578888399 71.3967000000) (40 . 0.0000000000) (41 . 0.0000000000) (42 . 0.0000000000) (91 . 0) (10 1658.3578888399 71.3967000000) (40 . 0.0000000000) (41 . 0.0000000000) (42 . 0.0000000000) (91 . 0) (10 1658.3578888399 72.8917774718) (40 . 0.0000000000) (41 . 0.0000000000) (42 . 0.0000000000) (91 . 0) (10 1672.3578888399 72.8917774718) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 1667.5828888399 51.5494120805 0.0000000000) (11 1667.5828888399 52.4429549452 0.0000000000) (210 0.0000000000 0.0000000000 1.0000000000))
((0 . "LINE") (100 . "AcDbEntity") (67 . 0) (8 . "A-Window") (62 . 151) (6 . "Continuous") (100 . "AcDbLine") (10 1663.1328888399 50.5796136866 0.0000000000) (11 1663.1328888399 51.4731565513 0.0000000000) (210 0.0000000000 0.0000000000 1.0000000000))
((0 . "LINE") (100 . "AcDbEntity") (67 . 0) (8 . "A-Window") (62 . 151) (6 . "Continuous") (100 . "AcDbLine") (10 1667.5828888399 51.5494120805 0.0000000000) (11 1667.5828888399 52.4429549452 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1663.1328888399 50.5796136866) (40 . 0.0000000000) (41 . 0.0000000000) (42 . 0.0000000000) (91 . 0) (10 1662.6078888399 50.1913851190) (40 . 0.0000000000) (41 . 0.0000000000) (42 . 0.0000000000) (91 . 0) (10 1663.1328888399 49.8031565513) (40 . 0.0000000000) (41 . 0.0000000000) (42 . 0.0000000000) (91 . 0) (10 1667.5828888399 50.7729549452) (40 . 0.0000000000) (41 . 0.0000000000) (42 . 0.0000000000) (91 . 0) (10 1668.1078888399 51.1611835129) (40 . 0.0000000000) (41 . 0.0000000000) (42 . 0.0000000000) (91 . 0) (10 1667.5828888399 51.5494120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 1668.1078888399 51.1611835129 0.0000000000) (11 1662.6078888399 50.1913851190 0.0000000000) (210 0.0000000000 0.0000000000 1.0000000000))
((0 . "LINE") (100 . "AcDbEntity") (67 . 0) (8 . "A-Window") (62 . 151) (6 . "Continuous") (100 . "AcDbLine") (10 1667.5828888399 49.8794120805 0.0000000000) (11 1667.5828888399 50.7729549452 0.0000000000) (210 0.0000000000 0.0000000000 1.0000000000))
((0 . "LINE") (100 . "AcDbEntity") (67 . 0) (8 . "A-Window") (62 . 151) (6 . "Continuous") (100 . "AcDbLine") (10 1663.1328888399 48.9096136866 0.0000000000) (11 1663.1328888399 49.8031565513 0.0000000000) (210 0.0000000000 0.0000000000 1.0000000000))
((0 . "LINE") (100 . "AcDbEntity") (67 . 0) (8 . "A-Window") (62 . 151) (6 . "Continuous") (100 . "AcDbLine") (10 1667.5828888399 49.8794120805 0.0000000000) (11 1667.5828888399 50.7729549452 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 1663.1328888399 48.9096136866) (40 . 0.0000000000) (41 . 0.0000000000) (42 . 0.0000000000) (91 . 0) (10 1662.6078888399 48.5213851190) (40 . 0.0000000000) (41 . 0.0000000000) (42 . 0.0000000000) (91 . 0) (10 1663.1328888399 48.1331565513) (40 . 0.0000000000) (41 . 0.0000000000) (42 . 0.0000000000) (91 . 0) (10 1667.5828888399 49.1029549452) (40 . 0.0000000000) (41 . 0.0000000000) (42 . 0.0000000000) (91 . 0) (10 1668.1078888399 49.4911835129) (40 . 0.0000000000) (41 . 0.0000000000) (42 . 0.0000000000) (91 . 0) (10 1667.5828888399 49.8794120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 1668.1078888399 49.4911835129 0.0000000000) (11 1662.6078888399 48.5213851190 0.0000000000) (210 0.0000000000 0.0000000000 1.0000000000))
((0 . "ARC") (100 . "AcDbEntity") (67 . 0) (8 . "A-Window") (62 . 151) (6 . "Continuous") (100 . "AcDbCircle") (10 1622.1876037977 66.7859023315 0.0000000000) (40 . 10.6781898097) (210 0.0000000000 0.0000000000 1.0000000000) (100 . "AcDbArc") (50 . -0.3727943380) (51 . 0.0384802174))
((0 . "LINE") (100 . "AcDbEntity") (67 . 0) (8 . "A-Window") (62 . 151) (6 . "Continuous") (100 . "AcDbLine") (10 1697.8578888398 38.1967000000 0.0000000000) (11 1697.8578888398 42.8966999996 0.0000000000) (210 0.0000000000 0.0000000000 1.0000000000))
((0 . "LWPOLYLINE") (100 . "AcDbEntity") (67 . 0) (8 . "A-Window") (62 . 3) (6 . "Continuous") (100 . "AcDbPolyline") (90 . 44) (70 . 1) (43 . 0.0000000000) (38 . 0.0000000000) (39 . 0.0000000000) (10 1689.3642583624 70.2966877930) (40 . 0.0000000000) (41 . 0.0000000000) (42 . 0.0000000000) (91 . 0) (10 1689.3642583624 70.0967122071) (40 . 0.0000000000) (41 . 0.0000000000) (42 . 0.4142225008) (91 . 0) (10 1689.7642583623 69.6967000001) (40 . 0.0000000000) (41 . 0.0000000000) (42 . 0.0000000000) (91 . 0) (10 1689.9642583623 69.6967000001) (40 . 0.0000000000) (41 . 0.0000000000) (42 . -0.4142135624) (91 . 0) (10 1690.5642583623 69.0967000001) (40 . 0.0000000000) (41 . 0.0000000000) (42 . 0.0000000000) (91 . 0) (10 1690.5642583623 68.8967000001) (40 . 0.0000000000) (41 . 0.0000000000) (42 . -0.2513806714) (91 . 0) (10 1690.2959208413 68.3967000001) (40 . 0.0000000000) (41 . 0.0000000000) (42 . 0.0000000000) (91 . 0) (10 1688.5640841376 68.3967000001) (40 . 0.0000000000) (41 . 0.0000000000) (42 . 0.4142135624) (91 . 0) (10 1688.0640841376 67.8967000001) (40 . 0.0000000000) (41 . 0.0000000000) (42 . 0.0000000000) (91 . 0) (10 1688.0640841376 63.2967000001) (40 . 0.0000000000) (41 . 0.0000000000) (42 . 0.4142135624) (91 . 0) (10 1688.5640841377 62.7967000001) (40 . 0.0000000000) (41 . 0.0000000000) (42 . 0.0000000000) (91 . 0) (10 1688.7742880937 62.7967000001) (40 . 0.0000000000) (41 . 0.0000000000) (42 . 0.0000000000) (91 . 0) (10 1688.9189729891 63.1989988507) (40 . 0.0000000000) (41 . 0.0000000000) (42 . 0.0000000000) (91 . 0) (10 1689.2762104021 63.1989988507) (40 . 0.0000000000) (41 . 0.0000000000) (42 . 0.0000000000) (91 . 0) (10 1689.4159547604 62.7967000001) (40 . 0.0000000000) (41 . 0.0000000000) (42 . 0.0000000000) (91 . 0) (10 1690.0576214270 62.7967000001) (40 . 0.0000000000) (41 . 0.0000000000) (42 . 0.0000000000) (91 . 0) (10 1690.2023063224 63.1989988507) (40 . 0.0000000000) (41 . 0.0000000000) (42 . 0.0000000000) (91 . 0) (10 1690.5595437354 63.1989988507) (40 . 0.0000000000) (41 . 0.0000000000) (42 . 0.0000000000) (91 . 0) (10 1690.6992880937 62.7967000001) (40 . 0.0000000000) (41 . 0.0000000000) (42 . 0.0000000000) (91 . 0) (10 1691.3409547603 62.7967000001) (40 . 0.0000000000) (41 . 0.0000000000) (42 . 0.0000000000) (91 . 0) (10 1691.4856396558 63.1989988507) (40 . 0.0000000000) (41 . 0.0000000000) (42 . 0.0000000000) (91 . 0) (10 1691.8428770688 63.1989988507) (40 . 0.0000000000) (41 . 0.0000000000) (42 . 0.0000000000) (91 . 0) (10 1691.9826214270 62.7967000001) (40 . 0.0000000000) (41 . 0.0000000000) (42 . 0.0000000000) (91 . 0) (10 1692.6242880937 62.7967000001) (40 . 0.0000000000) (41 . 0.0000000000) (42 . 0.0000000000) (91 . 0) (10 1692.7689729891 63.1989988507) (40 . 0.0000000000) (41 . 0.0000000000) (42 . 0.0000000000) (91 . 0) (10 1693.1262104021 63.1989988507) (40 . 0.0000000000) (41 . 0.0000000000) (42 . 0.0000000000) (91 . 0) (10 1693.2659547603 62.7967000001) (40 . 0.0000000000) (41 . 0.0000000000) (42 . 0.0000000000) (91 . 0) (10 1693.9076214270 62.7967000001) (40 . 0.0000000000) (41 . 0.0000000000) (42 . 0.0000000000) (91 . 0) (10 1694.0523063224 63.1989988507) (40 . 0.0000000000) (41 . 0.0000000000) (42 . 0.0000000000) (91 . 0) (10 1694.4095437354 63.1989988507) (40 . 0.0000000000) (41 . 0.0000000000) (42 . 0.0000000000) (91 . 0) (10 1694.5492880937 62.7967000001) (40 . 0.0000000000) (41 . 0.0000000000) (42 . 0.0000000000) (91 . 0) (10 1694.7640841376 62.7967000001) (40 . 0.0000000000) (41 . 0.0000000000) (42 . 0.4142135624) (91 . 0) (10 1695.2640841376 63.2967000001) (40 . 0.0000000000) (41 . 0.0000000000) (42 . 0.0000000000) (91 . 0) (10 1695.2640841376 67.8967000001) (40 . 0.0000000000) (41 . 0.0000000000) (42 . 0.4142135624) (91 . 0) (10 1694.7640841376 68.3967000001) (40 . 0.0000000000) (41 . 0.0000000000) (42 . 0.0000000000) (91 . 0) (10 1693.0325958832 68.3967000001) (40 . 0.0000000000) (41 . 0.0000000000) (42 . -0.2513806714) (91 . 0) (10 1692.7642583623 68.8967000001) (40 . 0.0000000000) (41 . 0.0000000000) (42 . 0.0000000000) (91 . 0) (10 1692.7642583623 69.0967000001) (40 . 0.0000000000) (41 . 0.0000000000) (42 . -0.4142135624) (91 . 0) (10 1693.3642583623 69.6967000001) (40 . 0.0000000000) (41 . 0.0000000000) (42 . 0.0000000000) (91 . 0) (10 1693.5642583623 69.6967000001) (40 . 0.0000000000) (41 . 0.0000000000) (42 . 0.4142135624) (91 . 0) (10 1693.9642583623 70.0967000001) (40 . 0.0000000000) (41 . 0.0000000000) (42 . 0.0000000000) (91 . 0) (10 1693.9642583623 70.2967000001) (40 . 0.0000000000) (41 . 0.0000000000) (42 . 0.4142135624) (91 . 0) (10 1693.5642583623 70.6967000001) (40 . 0.0000000000) (41 . 0.0000000000) (42 . 0.0000000000) (91 . 0) (10 1689.7642583623 70.6967000001) (40 . 0.0000000000) (41 . 0.0000000000) (42 . 0.4142225008) (91 . 0) (210 0.0000000000 0.0000000000 1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 1693.8190841376 67.3467000001) (40 . 0.0000000000) (41 . 0.0000000000) (42 . 0.0000000000) (91 . 0) (10 1693.8190841376 64.2467000001) (40 . 0.0000000000) (41 . 0.0000000000) (42 . 0.0000000000) (91 . 0) (10 1692.3190841376 64.2467000001) (40 . 0.0000000000) (41 . 0.0000000000) (42 . 0.0000000000) (91 . 0) (10 1692.3190841376 67.3467000001) (40 . 0.0000000000) (41 . 0.0000000000) (42 . 0.0000000000) (91 . 0) (210 0.0000000000 0.0000000000 1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 1690.9690841376 67.3467000001) (40 . 0.0000000000) (41 . 0.0000000000) (42 . 0.0000000000) (91 . 0) (10 1690.9690841376 64.2467000001) (40 . 0.0000000000) (41 . 0.0000000000) (42 . 0.0000000000) (91 . 0) (10 1689.4690841376 64.2467000001) (40 . 0.0000000000) (41 . 0.0000000000) (42 . 0.0000000000) (91 . 0) (10 1689.4690841376 67.3467000001) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 1697.8676567476 62.3966999996 0.0000000000) (11 1697.8676567476 67.1967000011 0.0000000000) (210 0.0000000000 0.0000000000 1.0000000000))
((0 . "ARC") (100 . "AcDbEntity") (67 . 0) (8 . "A-Window") (62 . 151) (6 . "Continuous") (100 . "AcDbCircle") (10 1622.1876037977 38.2074976685 0.0000000000) (40 . 10.6781898097) (210 0.0000000000 0.0000000000 1.0000000000) (100 . "AcDbArc") (50 . -0.0384802174) (51 . 0.3727943380))
((0 . "LWPOLYLINE") (100 . "AcDbEntity") (67 . 0) (8 . "A-Window") (62 . 3) (6 . "Continuous") (100 . "AcDbPolyline") (90 . 44) (70 . 1) (43 . 0.0000000000) (38 . 0.0000000000) (39 . 0.0000000000) (10 1640.6306645307 34.6967122070) (40 . 0.0000000000) (41 . 0.0000000000) (42 . 0.0000000000) (91 . 0) (10 1640.6306645307 34.8966877930) (40 . 0.0000000000) (41 . 0.0000000000) (42 . 0.4142225008) (91 . 0) (10 1640.2306645308 35.2967000000) (40 . 0.0000000000) (41 . 0.0000000000) (42 . 0.0000000000) (91 . 0) (10 1640.0306645308 35.2967000000) (40 . 0.0000000000) (41 . 0.0000000000) (42 . -0.4142135624) (91 . 0) (10 1639.4306645308 35.8967000000) (40 . 0.0000000000) (41 . 0.0000000000) (42 . 0.0000000000) (91 . 0) (10 1639.4306645308 36.0967000000) (40 . 0.0000000000) (41 . 0.0000000000) (42 . -0.2513806714) (91 . 0) (10 1639.6990020518 36.5967000000) (40 . 0.0000000000) (41 . 0.0000000000) (42 . 0.0000000000) (91 . 0) (10 1641.4308387555 36.5967000000) (40 . 0.0000000000) (41 . 0.0000000000) (42 . 0.4142135624) (91 . 0) (10 1641.9308387555 37.0967000000) (40 . 0.0000000000) (41 . 0.0000000000) (42 . 0.0000000000) (91 . 0) (10 1641.9308387555 41.6967000000) (40 . 0.0000000000) (41 . 0.0000000000) (42 . 0.4142135624) (91 . 0) (10 1641.4308387554 42.1967000000) (40 . 0.0000000000) (41 . 0.0000000000) (42 . 0.0000000000) (91 . 0) (10 1641.2206347994 42.1967000000) (40 . 0.0000000000) (41 . 0.0000000000) (42 . 0.0000000000) (91 . 0) (10 1641.0759499040 41.7944011494) (40 . 0.0000000000) (41 . 0.0000000000) (42 . 0.0000000000) (91 . 0) (10 1640.7187124910 41.7944011494) (40 . 0.0000000000) (41 . 0.0000000000) (42 . 0.0000000000) (91 . 0) (10 1640.5789681327 42.1967000000) (40 . 0.0000000000) (41 . 0.0000000000) (42 . 0.0000000000) (91 . 0) (10 1639.9373014661 42.1967000000) (40 . 0.0000000000) (41 . 0.0000000000) (42 . 0.0000000000) (91 . 0) (10 1639.7926165707 41.7944011494) (40 . 0.0000000000) (41 . 0.0000000000) (42 . 0.0000000000) (91 . 0) (10 1639.4353791577 41.7944011494) (40 . 0.0000000000) (41 . 0.0000000000) (42 . 0.0000000000) (91 . 0) (10 1639.2956347994 42.1967000000) (40 . 0.0000000000) (41 . 0.0000000000) (42 . 0.0000000000) (91 . 0) (10 1638.6539681328 42.1967000000) (40 . 0.0000000000) (41 . 0.0000000000) (42 . 0.0000000000) (91 . 0) (10 1638.5092832373 41.7944011494) (40 . 0.0000000000) (41 . 0.0000000000) (42 . 0.0000000000) (91 . 0) (10 1638.1520458243 41.7944011494) (40 . 0.0000000000) (41 . 0.0000000000) (42 . 0.0000000000) (91 . 0) (10 1638.0123014661 42.1967000000) (40 . 0.0000000000) (41 . 0.0000000000) (42 . 0.0000000000) (91 . 0) (10 1637.3706347994 42.1967000000) (40 . 0.0000000000) (41 . 0.0000000000) (42 . 0.0000000000) (91 . 0) (10 1637.2259499040 41.7944011494) (40 . 0.0000000000) (41 . 0.0000000000) (42 . 0.0000000000) (91 . 0) (10 1636.8687124910 41.7944011494) (40 . 0.0000000000) (41 . 0.0000000000) (42 . 0.0000000000) (91 . 0) (10 1636.7289681328 42.1967000000) (40 . 0.0000000000) (41 . 0.0000000000) (42 . 0.0000000000) (91 . 0) (10 1636.0873014661 42.1967000000) (40 . 0.0000000000) (41 . 0.0000000000) (42 . 0.0000000000) (91 . 0) (10 1635.9426165707 41.7944011494) (40 . 0.0000000000) (41 . 0.0000000000) (42 . 0.0000000000) (91 . 0) (10 1635.5853791577 41.7944011494) (40 . 0.0000000000) (41 . 0.0000000000) (42 . 0.0000000000) (91 . 0) (10 1635.4456347994 42.1967000000) (40 . 0.0000000000) (41 . 0.0000000000) (42 . 0.0000000000) (91 . 0) (10 1635.2308387555 42.1967000000) (40 . 0.0000000000) (41 . 0.0000000000) (42 . 0.4142135624) (91 . 0) (10 1634.7308387555 41.6967000000) (40 . 0.0000000000) (41 . 0.0000000000) (42 . 0.0000000000) (91 . 0) (10 1634.7308387555 37.0967000000) (40 . 0.0000000000) (41 . 0.0000000000) (42 . 0.4142135624) (91 . 0) (10 1635.2308387555 36.5967000000) (40 . 0.0000000000) (41 . 0.0000000000) (42 . 0.0000000000) (91 . 0) (10 1636.9623270099 36.5967000000) (40 . 0.0000000000) (41 . 0.0000000000) (42 . -0.2513806714) (91 . 0) (10 1637.2306645308 36.0967000000) (40 . 0.0000000000) (41 . 0.0000000000) (42 . 0.0000000000) (91 . 0) (10 1637.2306645308 35.8967000000) (40 . 0.0000000000) (41 . 0.0000000000) (42 . -0.4142135624) (91 . 0) (10 1636.6306645308 35.2967000000) (40 . 0.0000000000) (41 . 0.0000000000) (42 . 0.0000000000) (91 . 0) (10 1636.4306645308 35.2967000000) (40 . 0.0000000000) (41 . 0.0000000000) (42 . 0.4142135624) (91 . 0) (10 1636.0306645308 34.8967000000) (40 . 0.0000000000) (41 . 0.0000000000) (42 . 0.0000000000) (91 . 0) (10 1636.0306645308 34.6967000000) (40 . 0.0000000000) (41 . 0.0000000000) (42 . 0.4142135624) (91 . 0) (10 1636.4306645308 34.2967000000) (40 . 0.0000000000) (41 . 0.0000000000) (42 . 0.0000000000) (91 . 0) (10 1640.2306645308 34.2967000000) (40 . 0.0000000000) (41 . 0.0000000000) (42 . 0.4142225008) (91 . 0) (210 0.0000000000 0.0000000000 1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 1636.1758387555 37.6467000000) (40 . 0.0000000000) (41 . 0.0000000000) (42 . 0.0000000000) (91 . 0) (10 1636.1758387555 40.7467000000) (40 . 0.0000000000) (41 . 0.0000000000) (42 . 0.0000000000) (91 . 0) (10 1637.6758387555 40.7467000000) (40 . 0.0000000000) (41 . 0.0000000000) (42 . 0.0000000000) (91 . 0) (10 1637.6758387555 37.6467000000) (40 . 0.0000000000) (41 . 0.0000000000) (42 . 0.0000000000) (91 . 0) (210 0.0000000000 0.0000000000 1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 1639.0258387555 37.6467000000) (40 . 0.0000000000) (41 . 0.0000000000) (42 . 0.0000000000) (91 . 0) (10 1639.0258387555 40.7467000000) (40 . 0.0000000000) (41 . 0.0000000000) (42 . 0.0000000000) (91 . 0) (10 1640.5258387555 40.7467000000) (40 . 0.0000000000) (41 . 0.0000000000) (42 . 0.0000000000) (91 . 0) (10 1640.5258387555 37.6467000000) (40 . 0.0000000000) (41 . 0.0000000000) (42 . 0.0000000000) (91 . 0) (210 0.0000000000 0.0000000000 1.0000000000))
((0 . "LWPOLYLINE") (100 . "AcDbEntity") (67 . 0) (8 . "A-Window") (62 . 3) (6 . "Continuous") (100 . "AcDbPolyline") (90 . 44) (70 . 1) (43 . 0.0000000000) (38 . 0.0000000000) (39 . 0.0000000000) (10 -1690.0851131491 34.6967122070) (40 . 0.0000000000) (41 . 0.0000000000) (42 . 0.0000000000) (91 . 0) (10 -1690.0851131491 34.8966877930) (40 . 0.0000000000) (41 . 0.0000000000) (42 . 0.4142225008) (91 . 0) (10 -1690.4851131490 35.2967000000) (40 . 0.0000000000) (41 . 0.0000000000) (42 . 0.0000000000) (91 . 0) (10 -1690.6851131490 35.2967000000) (40 . 0.0000000000) (41 . 0.0000000000) (42 . -0.4142135624) (91 . 0) (10 -1691.2851131490 35.8967000000) (40 . 0.0000000000) (41 . 0.0000000000) (42 . 0.0000000000) (91 . 0) (10 -1691.2851131490 36.0967000000) (40 . 0.0000000000) (41 . 0.0000000000) (42 . -0.2513806714) (91 . 0) (10 -1691.0167756280 36.5967000000) (40 . 0.0000000000) (41 . 0.0000000000) (42 . 0.0000000000) (91 . 0) (10 -1689.2849389243 36.5967000000) (40 . 0.0000000000) (41 . 0.0000000000) (42 . 0.4142135624) (91 . 0) (10 -1688.7849389243 37.0967000000) (40 . 0.0000000000) (41 . 0.0000000000) (42 . 0.0000000000) (91 . 0) (10 -1688.7849389243 41.6967000000) (40 . 0.0000000000) (41 . 0.0000000000) (42 . 0.4142135624) (91 . 0) (10 -1689.2849389244 42.1967000000) (40 . 0.0000000000) (41 . 0.0000000000) (42 . 0.0000000000) (91 . 0) (10 -1689.4951428804 42.1967000000) (40 . 0.0000000000) (41 . 0.0000000000) (42 . 0.0000000000) (91 . 0) (10 -1689.6398277758 41.7944011494) (40 . 0.0000000000) (41 . 0.0000000000) (42 . 0.0000000000) (91 . 0) (10 -1689.9970651888 41.7944011494) (40 . 0.0000000000) (41 . 0.0000000000) (42 . 0.0000000000) (91 . 0) (10 -1690.1368095471 42.1967000000) (40 . 0.0000000000) (41 . 0.0000000000) (42 . 0.0000000000) (91 . 0) (10 -1690.7784762137 42.1967000000) (40 . 0.0000000000) (41 . 0.0000000000) (42 . 0.0000000000) (91 . 0) (10 -1690.9231611091 41.7944011494) (40 . 0.0000000000) (41 . 0.0000000000) (42 . 0.0000000000) (91 . 0) (10 -1691.2803985221 41.7944011494) (40 . 0.0000000000) (41 . 0.0000000000) (42 . 0.0000000000) (91 . 0) (10 -1691.4201428804 42.1967000000) (40 . 0.0000000000) (41 . 0.0000000000) (42 . 0.0000000000) (91 . 0) (10 -1692.0618095471 42.1967000000) (40 . 0.0000000000) (41 . 0.0000000000) (42 . 0.0000000000) (91 . 0) (10 -1692.2064944425 41.7944011494) (40 . 0.0000000000) (41 . 0.0000000000) (42 . 0.0000000000) (91 . 0) (10 -1692.5637318555 41.7944011494) (40 . 0.0000000000) (41 . 0.0000000000) (42 . 0.0000000000) (91 . 0) (10 -1692.7034762137 42.1967000000) (40 . 0.0000000000) (41 . 0.0000000000) (42 . 0.0000000000) (91 . 0) (10 -1693.3451428804 42.1967000000) (40 . 0.0000000000) (41 . 0.0000000000) (42 . 0.0000000000) (91 . 0) (10 -1693.4898277758 41.7944011494) (40 . 0.0000000000) (41 . 0.0000000000) (42 . 0.0000000000) (91 . 0) (10 -1693.8470651888 41.7944011494) (40 . 0.0000000000) (41 . 0.0000000000) (42 . 0.0000000000) (91 . 0) (10 -1693.9868095471 42.1967000000) (40 . 0.0000000000) (41 . 0.0000000000) (42 . 0.0000000000) (91 . 0) (10 -1694.6284762137 42.1967000000) (40 . 0.0000000000) (41 . 0.0000000000) (42 . 0.0000000000) (91 . 0) (10 -1694.7731611091 41.7944011494) (40 . 0.0000000000) (41 . 0.0000000000) (42 . 0.0000000000) (91 . 0) (10 -1695.1303985221 41.7944011494) (40 . 0.0000000000) (41 . 0.0000000000) (42 . 0.0000000000) (91 . 0) (10 -1695.2701428804 42.1967000000) (40 . 0.0000000000) (41 . 0.0000000000) (42 . 0.0000000000) (91 . 0) (10 -1695.4849389243 42.1967000000) (40 . 0.0000000000) (41 . 0.0000000000) (42 . 0.4142135624) (91 . 0) (10 -1695.9849389243 41.6967000000) (40 . 0.0000000000) (41 . 0.0000000000) (42 . 0.0000000000) (91 . 0) (10 -1695.9849389243 37.0967000000) (40 . 0.0000000000) (41 . 0.0000000000) (42 . 0.4142135624) (91 . 0) (10 -1695.4849389243 36.5967000000) (40 . 0.0000000000) (41 . 0.0000000000) (42 . 0.0000000000) (91 . 0) (10 -1693.7534506699 36.5967000000) (40 . 0.0000000000) (41 . 0.0000000000) (42 . -0.2513806714) (91 . 0) (10 -1693.4851131490 36.0967000000) (40 . 0.0000000000) (41 . 0.0000000000) (42 . 0.0000000000) (91 . 0) (10 -1693.4851131490 35.8967000000) (40 . 0.0000000000) (41 . 0.0000000000) (42 . -0.4142135624) (91 . 0) (10 -1694.0851131490 35.2967000000) (40 . 0.0000000000) (41 . 0.0000000000) (42 . 0.0000000000) (91 . 0) (10 -1694.2851131490 35.2967000000) (40 . 0.0000000000) (41 . 0.0000000000) (42 . 0.4142135624) (91 . 0) (10 -1694.6851131490 34.8967000000) (40 . 0.0000000000) (41 . 0.0000000000) (42 . 0.0000000000) (91 . 0) (10 -1694.6851131490 34.6967000000) (40 . 0.0000000000) (41 . 0.0000000000) (42 . 0.4142135624) (91 . 0) (10 -1694.2851131490 34.2967000000) (40 . 0.0000000000) (41 . 0.0000000000) (42 . 0.0000000000) (91 . 0) (10 -1690.4851131490 34.2967000000) (40 . 0.0000000000) (41 . 0.0000000000) (42 . 0.4142225008) (91 . 0) (210 0.0000000000 0.0000000000 -1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 -1694.5399389243 37.6467000000) (40 . 0.0000000000) (41 . 0.0000000000) (42 . 0.0000000000) (91 . 0) (10 -1694.5399389243 40.7467000000) (40 . 0.0000000000) (41 . 0.0000000000) (42 . 0.0000000000) (91 . 0) (10 -1693.0399389243 40.7467000000) (40 . 0.0000000000) (41 . 0.0000000000) (42 . 0.0000000000) (91 . 0) (10 -1693.0399389243 37.6467000000) (40 . 0.0000000000) (41 . 0.0000000000) (42 . 0.0000000000) (91 . 0) (210 0.0000000000 0.0000000000 -1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 -1691.6899389243 37.6467000000) (40 . 0.0000000000) (41 . 0.0000000000) (42 . 0.0000000000) (91 . 0) (10 -1691.6899389243 40.7467000000) (40 . 0.0000000000) (41 . 0.0000000000) (42 . 0.0000000000) (91 . 0) (10 -1690.1899389243 40.7467000000) (40 . 0.0000000000) (41 . 0.0000000000) (42 . 0.0000000000) (91 . 0) (10 -1690.1899389243 37.6467000000) (40 . 0.0000000000) (41 . 0.0000000000) (42 . 0.0000000000) (91 . 0) (210 0.0000000000 0.0000000000 -1.0000000000))
((0 . "LWPOLYLINE") (100 . "AcDbEntity") (67 . 0) (8 . "A-Window") (62 . 151) (6 . "Continuous") (100 . "AcDbPolyline") (90 . 8) (70 . 1) (43 . 0.0000000000) (38 . 0.0000000000) (39 . 0.0000000000) (10 29.8578888394 -90.5967000000) (40 . 0.0000000000) (41 . 0.0000000000) (42 . 0.4142135624) (91 . 0) (10 30.3578888394 -90.0967000000) (40 . 0.0000000000) (41 . 0.0000000000) (42 . 0.0000000000) (91 . 0) (10 30.3578888394 30.4967000000) (40 . 0.0000000000) (41 . 0.0000000000) (42 . 0.4142135624) (91 . 0) (10 29.8578888394 30.9967000000) (40 . 0.0000000000) (41 . 0.0000000000) (42 . 0.0000000000) (91 . 0) (10 -29.1421111606 30.9967000000) (40 . 0.0000000000) (41 . 0.0000000000) (42 . 0.4142135624) (91 . 0) (10 -29.6421111606 30.4967000000) (40 . 0.0000000000) (41 . 0.0000000000) (42 . 0.0000000000) (91 . 0) (10 -29.6421111606 -90.0967000000) (40 . 0.0000000000) (41 . 0.0000000000) (42 . 0.4142135624) (91 . 0) (10 -29.1421111606 -90.5967000000) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 87) (70 . 1) (43 . 0.0000000000) (38 . 0.0000000000) (39 . 0.0000000000) (10 29.7578888394 34.6967000000) (40 . 0.0000000000) (41 . 0.0000000000) (42 . 0.0000000000) (91 . 0) (10 29.7578888394 34.4967000000) (40 . 0.0000000000) (41 . 0.0000000000) (42 . -0.4142135624) (91 . 0) (10 29.2578888394 33.9967000000) (40 . 0.0000000000) (41 . 0.0000000000) (42 . 0.0000000000) (91 . 0) (10 25.4578888394 33.9967000000) (40 . 0.0000000000) (41 . 0.0000000000) (42 . -0.4142135624) (91 . 0) (10 24.9578888394 34.4967000000) (40 . 0.0000000000) (41 . 0.0000000000) (42 . 0.0000000000) (91 . 0) (10 24.9578888394 34.6967000000) (40 . 0.0000000000) (41 . 0.0000000000) (42 . -0.4142135624) (91 . 0) (10 25.4578888394 35.1967000000) (40 . 0.0000000000) (41 . 0.0000000000) (42 . 0.0000000000) (91 . 0) (10 25.6578888394 35.1967000000) (40 . 0.0000000000) (41 . 0.0000000000) (42 . 0.4142135624) (91 . 0) (10 26.1578888394 35.6967000000) (40 . 0.0000000000) (41 . 0.0000000000) (42 . 0.0000000000) (91 . 0) (10 26.1578888394 35.8967000000) (40 . 0.0000000000) (41 . 0.0000000000) (42 . 0.4142135624) (91 . 0) (10 25.6578888394 36.3967000000) (40 . 0.0000000000) (41 . 0.0000000000) (42 . 0.0000000000) (91 . 0) (10 24.2578888394 36.3967000000) (40 . 0.0000000000) (41 . 0.0000000000) (42 . 0.4142135624) (91 . 0) (10 23.7578888394 35.8967000000) (40 . 0.0000000000) (41 . 0.0000000000) (42 . 0.0000000000) (91 . 0) (10 23.7578888394 34.4967000000) (40 . 0.0000000000) (41 . 0.0000000000) (42 . -0.4142135624) (91 . 0) (10 23.2578888394 33.9967000000) (40 . 0.0000000000) (41 . 0.0000000000) (42 . 0.0000000000) (91 . 0) (10 9.3578888394 33.9967000000) (40 . 0.0000000000) (41 . 0.0000000000) (42 . -0.4142135624) (91 . 0) (10 8.8578888394 34.4967000000) (40 . 0.0000000000) (41 . 0.0000000000) (42 . 0.0000000000) (91 . 0) (10 8.8578888394 55.8967000000) (40 . 0.0000000000) (41 . 0.0000000000) (42 . 0.4142135624) (91 . 0) (10 8.3578888394 56.3967000000) (40 . 0.0000000000) (41 . 0.0000000000) (42 . 0.0000000000) (91 . 0) (10 6.0578936442 56.3967000000) (40 . 0.0000000000) (41 . 0.0000000000) (42 . 0.0000000000) (91 . 0) (10 5.0809431613 54.4427990332) (40 . 0.0000000000) (41 . 0.0000000000) (42 . 0.4142135643) (91 . 0) (10 5.1703858816 54.1744708754) (40 . 0.0000000000) (41 . 0.0000000000) (42 . 0.0000000000) (91 . 0) (10 5.3492713179 54.0850281587) (40 . 0.0000000000) (41 . 0.0000000000) (42 . -0.4142135643) (91 . 0) (10 5.4387140381 53.8167000008) (40 . 0.0000000000) (41 . 0.0000000000) (42 . 0.0000000000) (91 . 0) (10 4.8339926779 52.6072572806) (40 . 0.0000000000) (41 . 0.0000000000) (42 . -0.2840790438) (91 . 0) (10 4.6551072397 52.4966999997) (40 . 0.0000000000) (41 . 0.0000000000) (42 . 0.0000000000) (91 . 0) (10 1.0235742645 52.4966999997) (40 . 0.0000000000) (41 . 0.0000000000) (42 . 0.1989123674) (91 . 0) (10 0.8821529082 52.4381213559) (40 . 0.0000000000) (41 . 0.0000000000) (42 . 0.0000000000) (91 . 0) (10 0.4993101957 52.0552786434) (40 . 0.0000000000) (41 . 0.0000000000) (42 . -0.1989123674) (91 . 0) (10 0.3578888395 51.9966999997) (40 . 0.0000000000) (41 . 0.0000000000) (42 . -0.1989123674) (91 . 0) (10 0.2164674833 52.0552786434) (40 . 0.0000000000) (41 . 0.0000000000) (42 . 0.0000000000) (91 . 0) (10 -0.1663752292 52.4381213559) (40 . 0.0000000000) (41 . 0.0000000000) (42 . 0.1989123674) (91 . 0) (10 -0.3077965854 52.4966999997) (40 . 0.0000000000) (41 . 0.0000000000) (42 . 0.0000000000) (91 . 0) (10 -3.9393295607 52.4966999997) (40 . 0.0000000000) (41 . 0.0000000000) (42 . -0.2840790438) (91 . 0) (10 -4.1182149988 52.6072572805) (40 . 0.0000000000) (41 . 0.0000000000) (42 . 0.0000000000) (91 . 0) (10 -4.7229363593 53.8167000007) (40 . 0.0000000000) (41 . 0.0000000000) (42 . -0.4142135642) (91 . 0) (10 -4.6334936391 54.0850281586) (40 . 0.0000000000) (41 . 0.0000000000) (42 . 0.0000000000) (91 . 0) (10 -4.4546082026 54.1744708755) (40 . 0.0000000000) (41 . 0.0000000000) (42 . 0.4142135641) (91 . 0) (10 -4.3651654824 54.4427990333) (40 . 0.0000000000) (41 . 0.0000000000) (42 . 0.0000000000) (91 . 0) (10 -5.3421159653 56.3967000000) (40 . 0.0000000000) (41 . 0.0000000000) (42 . 0.0000000000) (91 . 0) (10 -7.6421111606 56.3967000000) (40 . 0.0000000000) (41 . 0.0000000000) (42 . 0.4142135624) (91 . 0) (10 -8.1421111606 55.8967000000) (40 . 0.0000000000) (41 . 0.0000000000) (42 . 0.0000000000) (91 . 0) (10 -8.1421111606 34.4967000000) (40 . 0.0000000000) (41 . 0.0000000000) (42 . -0.4142135624) (91 . 0) (10 -8.6421111606 33.9967000000) (40 . 0.0000000000) (41 . 0.0000000000) (42 . 0.0000000000) (91 . 0) (10 -22.5421111606 33.9967000000) (40 . 0.0000000000) (41 . 0.0000000000) (42 . -0.4142135624) (91 . 0) (10 -23.0421111606 34.4967000000) (40 . 0.0000000000) (41 . 0.0000000000) (42 . 0.0000000000) (91 . 0) (10 -23.0421111606 35.8967000000) (40 . 0.0000000000) (41 . 0.0000000000) (42 . 0.4142135624) (91 . 0) (10 -23.5421111606 36.3967000000) (40 . 0.0000000000) (41 . 0.0000000000) (42 . 0.0000000000) (91 . 0) (10 -24.9421111606 36.3967000000) (40 . 0.0000000000) (41 . 0.0000000000) (42 . 0.4142135624) (91 . 0) (10 -25.4421111606 35.8967000000) (40 . 0.0000000000) (41 . 0.0000000000) (42 . 0.0000000000) (91 . 0) (10 -25.4421111606 35.6967000000) (40 . 0.0000000000) (41 . 0.0000000000) (42 . 0.4142135624) (91 . 0) (10 -24.9421111606 35.1967000000) (40 . 0.0000000000) (41 . 0.0000000000) (42 . 0.0000000000) (91 . 0) (10 -24.7421111606 35.1967000000) (40 . 0.0000000000) (41 . 0.0000000000) (42 . -0.4142135624) (91 . 0) (10 -24.2421111606 34.6967000000) (40 . 0.0000000000) (41 . 0.0000000000) (42 . 0.0000000000) (91 . 0) (10 -24.2421111606 34.4967000000) (40 . 0.0000000000) (41 . 0.0000000000) (42 . -0.4142135624) (91 . 0) (10 -24.7421111606 33.9967000000) (40 . 0.0000000000) (41 . 0.0000000000) (42 . 0.0000000000) (91 . 0) (10 -28.5421111606 33.9967000000) (40 . 0.0000000000) (41 . 0.0000000000) (42 . -0.4142135624) (91 . 0) (10 -29.0421111606 34.4967000000) (40 . 0.0000000000) (41 . 0.0000000000) (42 . 0.0000000000) (91 . 0) (10 -29.0421111606 34.6967000000) (40 . 0.0000000000) (41 . 0.0000000000) (42 . -0.4142135624) (91 . 0) (10 -28.5421111606 35.1967000000) (40 . 0.0000000000) (41 . 0.0000000000) (42 . 0.0000000000) (91 . 0) (10 -28.3421111606 35.1967000000) (40 . 0.0000000000) (41 . 0.0000000000) (42 . 0.4142135624) (91 . 0) (10 -27.8421111606 35.6967000000) (40 . 0.0000000000) (41 . 0.0000000000) (42 . 0.0000000000) (91 . 0) (10 -27.8421111606 35.8967000000) (40 . 0.0000000000) (41 . 0.0000000000) (42 . 0.4142135624) (91 . 0) (10 -28.3421111606 36.3967000000) (40 . 0.0000000000) (41 . 0.0000000000) (42 . 0.0000000000) (91 . 0) (10 -30.4421111606 36.3967000000) (40 . 0.0000000000) (41 . 0.0000000000) (42 . -0.4142135624) (91 . 0) (10 -30.9421111606 36.8967000000) (40 . 0.0000000000) (41 . 0.0000000000) (42 . 0.0000000000) (91 . 0) (10 -30.9421111606 37.8967000000) (40 . 0.0000000000) (41 . 0.0000000000) (42 . 0.4142135624) (91 . 0) (10 -31.4421111606 38.3967000000) (40 . 0.0000000000) (41 . 0.0000000000) (42 . 0.0000000000) (91 . 0) (10 -31.6421111606 38.3967000000) (40 . 0.0000000000) (41 . 0.0000000000) (42 . 0.4142135624) (91 . 0) (10 -32.1421111606 37.8967000000) (40 . 0.0000000000) (41 . 0.0000000000) (42 . 0.0000000000) (91 . 0) (10 -32.1421111606 33.9967000000) (40 . 0.0000000000) (41 . 0.0000000000) (42 . 0.0000000000) (91 . 0) (10 -32.1421111606 -93.0967000000) (40 . 0.0000000000) (41 . 0.0000000000) (42 . 0.4142135624) (91 . 0) (10 -31.6421111606 -93.5967000000) (40 . 0.0000000000) (41 . 0.0000000000) (42 . 0.0000000000) (91 . 0) (10 32.3578888394 -93.5967000000) (40 . 0.0000000000) (41 . 0.0000000000) (42 . 0.4142135624) (91 . 0) (10 32.8578888394 -93.0967000000) (40 . 0.0000000000) (41 . 0.0000000000) (42 . 0.0000000000) (91 . 0) (10 32.8578888394 33.9967000000) (40 . 0.0000000000) (41 . 0.0000000000) (42 . 0.0000000000) (91 . 0) (10 32.8578888394 37.8967000000) (40 . 0.0000000000) (41 . 0.0000000000) (42 . 0.4142135624) (91 . 0) (10 32.3578888394 38.3967000000) (40 . 0.0000000000) (41 . 0.0000000000) (42 . 0.0000000000) (91 . 0) (10 32.1578888394 38.3967000000) (40 . 0.0000000000) (41 . 0.0000000000) (42 . 0.4142135624) (91 . 0) (10 31.6578888394 37.8967000000) (40 . 0.0000000000) (41 . 0.0000000000) (42 . 0.0000000000) (91 . 0) (10 31.6578888394 36.8967000000) (40 . 0.0000000000) (41 . 0.0000000000) (42 . -0.4142135624) (91 . 0) (10 31.1578888394 36.3967000000) (40 . 0.0000000000) (41 . 0.0000000000) (42 . 0.0000000000) (91 . 0) (10 29.0578888394 36.3967000000) (40 . 0.0000000000) (41 . 0.0000000000) (42 . 0.4142135624) (91 . 0) (10 28.5578888394 35.8967000000) (40 . 0.0000000000) (41 . 0.0000000000) (42 . 0.0000000000) (91 . 0) (10 28.5578888394 35.6967000000) (40 . 0.0000000000) (41 . 0.0000000000) (42 . 0.4142135624) (91 . 0) (10 29.0578888394 35.1967000000) (40 . 0.0000000000) (41 . 0.0000000000) (42 . 0.0000000000) (91 . 0) (10 29.2578888394 35.1967000000) (40 . 0.0000000000) (41 . 0.0000000000) (42 . -0.4142135624) (91 . 0) (210 0.0000000000 0.0000000000 1.0000000000))
((0 . "LWPOLYLINE") (100 . "AcDbEntity") (67 . 0) (8 . "A-Window") (62 . 151) (6 . "Continuous") (100 . "AcDbPolyline") (90 . 17) (70 . 1) (43 . 0.0000000000) (38 . 0.0000000000) (39 . 0.0000000000) (10 0.3578888395 47.4966999996) (40 . 0.0000000000) (41 . 0.0000000000) (42 . 0.0000000000) (91 . 0) (10 -2.8235760300 47.4966999996) (40 . 0.0000000000) (41 . 0.0000000000) (42 . -0.2914734196) (91 . 0) (10 -3.2767299235 47.7853908688) (40 . 0.0000000000) (41 . 0.0000000000) (42 . 0.0000000000) (91 . 0) (10 -4.1732615427 49.7080091306) (40 . 0.0000000000) (41 . 0.0000000000) (42 . 0.2914734196) (91 . 0) (10 -4.6264154362 49.9966999997) (40 . 0.0000000000) (41 . 0.0000000000) (42 . 0.0000000000) (91 . 0) (10 -5.6421111605 49.9966999997) (40 . 0.0000000000) (41 . 0.0000000000) (42 . 0.4142135624) (91 . 0) (10 -6.1421111605 49.4966999997) (40 . 0.0000000000) (41 . 0.0000000000) (42 . 0.0000000000) (91 . 0) (10 -6.1421111605 34.4967000000) (40 . 0.0000000000) (41 . 0.0000000000) (42 . 0.4142135624) (91 . 0) (10 -5.6421111605 33.9967000000) (40 . 0.0000000000) (41 . 0.0000000000) (42 . 0.0000000000) (91 . 0) (10 6.3578888395 33.9967000000) (40 . 0.0000000000) (41 . 0.0000000000) (42 . 0.4142135624) (91 . 0) (10 6.8578888395 34.4967000000) (40 . 0.0000000000) (41 . 0.0000000000) (42 . 0.0000000000) (91 . 0) (10 6.8578888395 49.4966999997) (40 . 0.0000000000) (41 . 0.0000000000) (42 . 0.4142135624) (91 . 0) (10 6.3578888395 49.9966999997) (40 . 0.0000000000) (41 . 0.0000000000) (42 . 0.0000000000) (91 . 0) (10 5.3421931154 49.9966999997) (40 . 0.0000000000) (41 . 0.0000000000) (42 . 0.2914734196) (91 . 0) (10 4.8890392219 49.7080091306) (40 . 0.0000000000) (41 . 0.0000000000) (42 . 0.0000000000) (91 . 0) (10 3.9925076027 47.7853908688) (40 . 0.0000000000) (41 . 0.0000000000) (42 . -0.2914734196) (91 . 0) (10 3.5393537092 47.4966999996) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 12) (70 . 1) (43 . 0.0000000000) (38 . 0.0000000000) (39 . 0.0000000000) (10 6.1467510526 61.6983038651) (40 . 0.0000000000) (41 . 0.0000000000) (42 . 0.2849552787) (91 . 0) (10 6.2578888319 61.8774783771) (40 . 0.0000000000) (41 . 0.0000000000) (42 . 0.0000000000) (91 . 0) (10 6.2578888319 61.7734539608) (40 . 0.0000000000) (41 . 0.0000000000) (42 . 0.5564744028) (91 . 0) (10 5.5357332802 62.2213902406) (40 . 0.0000000000) (41 . 0.0000000000) (42 . 0.0000000000) (91 . 0) (10 0.5800443918 62.7635991465) (40 . 0.0000000000) (41 . 0.0000000000) (42 . -0.2343570514) (91 . 0) (10 0.1357332887 62.7635991463) (40 . 0.0000000000) (41 . 0.0000000000) (42 . 0.0000000000) (91 . 0) (10 -4.8199556166 62.2213902421) (40 . 0.0000000000) (41 . 0.0000000000) (42 . 0.5564744024) (91 . 0) (10 -5.5421111679 61.7734539620) (40 . 0.0000000000) (41 . 0.0000000000) (42 . 0.0000000000) (91 . 0) (10 -5.5421111679 61.8774783772) (40 . 0.0000000000) (41 . 0.0000000000) (42 . 0.2849552790) (91 . 0) (10 -5.4309733884 61.6983038651) (40 . 0.0000000000) (41 . 0.0000000000) (42 . 0.0000000000) (91 . 0) (10 0.1357332882 58.9374763869) (40 . 0.0000000000) (41 . 0.0000000000) (42 . 0.2343570514) (91 . 0) (10 0.5800443913 58.9374763871) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 65) (70 . 0) (43 . 0.0000000000) (38 . 0.0000000000) (39 . 0.0000000000) (10 4.8578888320 67.1313221971) (40 . 0.0000000000) (41 . 0.0000000000) (42 . 0.0000000000) (91 . 0) (10 4.8578888320 66.5967000000) (40 . 0.0000000000) (41 . 0.0000000000) (42 . 0.4142135624) (91 . 0) (10 5.0578888322 66.3967000000) (40 . 0.0000000000) (41 . 0.0000000000) (42 . 0.0000000000) (91 . 0) (10 6.0578888322 66.3967000000) (40 . 0.0000000000) (41 . 0.0000000000) (42 . -0.4142135624) (91 . 0) (10 6.2578888319 66.1967000000) (40 . 0.0000000000) (41 . 0.0000000000) (42 . 0.0000000000) (91 . 0) (10 6.2578888319 64.3779464253) (40 . 0.0000000000) (41 . 0.0000000000) (42 . -0.2849552787) (91 . 0) (10 6.1467510526 64.1987719134) (40 . 0.0000000000) (41 . 0.0000000000) (42 . 0.0000000000) (91 . 0) (10 0.5800443909 61.4379444351) (40 . 0.0000000000) (41 . 0.0000000000) (42 . -0.2343570514) (91 . 0) (10 0.1357332879 61.4379444349) (40 . 0.0000000000) (41 . 0.0000000000) (42 . 0.0000000000) (91 . 0) (10 -5.4309733884 64.1987719129) (40 . 0.0000000000) (41 . 0.0000000000) (42 . -0.2849552790) (91 . 0) (10 -5.5421111679 64.3779464250) (40 . 0.0000000000) (41 . 0.0000000000) (42 . 0.0000000000) (91 . 0) (10 -5.5421111679 66.1967000000) (40 . 0.0000000000) (41 . 0.0000000000) (42 . -0.4142135624) (91 . 0) (10 -5.3421111677 66.3966999999) (40 . 0.0000000000) (41 . 0.0000000000) (42 . 0.0000000000) (91 . 0) (10 -4.3421111677 66.3966999999) (40 . 0.0000000000) (41 . 0.0000000000) (42 . 0.4142135624) (91 . 0) (10 -4.1421111680 66.5967000000) (40 . 0.0000000000) (41 . 0.0000000000) (42 . 0.0000000000) (91 . 0) (10 -4.1421111680 67.1189032619) (40 . 0.0000000000) (41 . 0.0000000000) (42 . 0.1876437528) (91 . 0) (10 -4.1946803399 67.2540481876) (40 . 0.0000000000) (41 . 0.0000000000) (42 . 0.0000000000) (91 . 0) (10 -5.1826606833 68.3318449257) (40 . 0.0000000000) (41 . 0.0000000000) (42 . 0.2102297862) (91 . 0) (10 -5.3300915111 68.3966999999) (40 . 0.0000000000) (41 . 0.0000000000) (42 . 0.0000000000) (91 . 0) (10 -6.9421111678 68.3966999999) (40 . 0.0000000000) (41 . 0.0000000000) (42 . 0.4142135624) (91 . 0) (10 -7.1421111680 68.1967000000) (40 . 0.0000000000) (41 . 0.0000000000) (42 . 0.0000000000) (91 . 0) (10 -7.1421111680 56.5967000000) (40 . 0.0000000000) (41 . 0.0000000000) (42 . 0.4142135624) (91 . 0) (10 -6.9421111678 56.3966999999) (40 . 0.0000000000) (41 . 0.0000000000) (42 . 0.0000000000) (91 . 0) (10 -5.9421111678 56.3966999999) (40 . 0.0000000000) (41 . 0.0000000000) (42 . 0.4142135624) (91 . 0) (10 -5.7421111681 56.5967000000) (40 . 0.0000000000) (41 . 0.0000000000) (42 . 0.0000000000) (91 . 0) (10 -5.7421111681 59.0967000000) (40 . 0.0000000000) (41 . 0.0000000000) (42 . -0.5788431251) (91 . 0) (10 -4.9901756553 59.5285894504) (40 . 0.0000000000) (41 . 0.0000000000) (42 . 0.0000000000) (91 . 0) (10 -4.4199556161 59.2457868447) (40 . 0.0000000000) (41 . 0.0000000000) (42 . -0.2849552788) (91 . 0) (10 -4.1421111680 58.7978505647) (40 . 0.0000000000) (41 . 0.0000000000) (42 . 0.0000000000) (91 . 0) (10 -4.1421111680 54.3533563146) (40 . 0.0000000000) (41 . 0.0000000000) (42 . -0.2840790438) (91 . 0) (10 -4.2526684489 54.1744708764) (40 . 0.0000000000) (41 . 0.0000000000) (42 . 0.0000000000) (91 . 0) (10 -4.4315538869 54.0850281572) (40 . 0.0000000000) (41 . 0.0000000000) (42 . 0.4142135624) (91 . 0) (10 -4.5209966062 53.8167000000) (40 . 0.0000000000) (41 . 0.0000000000) (42 . 0.0000000000) (91 . 0) (10 -3.9162752462 52.6072572809) (40 . 0.0000000000) (41 . 0.0000000000) (42 . 0.2840790438) (91 . 0) (10 -3.7373898082 52.4967000000) (40 . 0.0000000000) (41 . 0.0000000000) (42 . 0.0000000000) (91 . 0) (10 -3.0609966062 52.4967000000) (40 . 0.0000000000) (41 . 0.0000000000) (42 . 0.4142135624) (91 . 0) (10 -2.8609966060 52.6967000000) (40 . 0.0000000000) (41 . 0.0000000000) (42 . 0.0000000000) (91 . 0) (10 -2.8609966060 57.9432778508) (40 . 0.0000000000) (41 . 0.0000000000) (42 . -0.5564744024) (91 . 0) (10 -2.1388410548 58.3912141310) (40 . 0.0000000000) (41 . 0.0000000000) (42 . 0.0000000000) (91 . 0) (10 0.2690266202 57.1970238086) (40 . 0.0000000000) (41 . 0.0000000000) (42 . 0.2343570514) (91 . 0) (10 0.4467510614 57.1970238087) (40 . 0.0000000000) (41 . 0.0000000000) (42 . 0.0000000000) (91 . 0) (10 2.8546187183 58.3912141254) (40 . 0.0000000000) (41 . 0.0000000000) (42 . -0.5564744028) (91 . 0) (10 3.5767742701 57.9432778455) (40 . 0.0000000000) (41 . 0.0000000000) (42 . 0.0000000000) (91 . 0) (10 3.5767742701 52.6967000000) (40 . 0.0000000000) (41 . 0.0000000000) (42 . 0.4142135624) (91 . 0) (10 3.7767742703 52.4967000000) (40 . 0.0000000000) (41 . 0.0000000000) (42 . 0.0000000000) (91 . 0) (10 4.4531674728 52.4967000000) (40 . 0.0000000000) (41 . 0.0000000000) (42 . 0.2840790438) (91 . 0) (10 4.6320529108 52.6072572809) (40 . 0.0000000000) (41 . 0.0000000000) (42 . 0.0000000000) (91 . 0) (10 5.2367742702 53.8167000000) (40 . 0.0000000000) (41 . 0.0000000000) (42 . 0.4142135624) (91 . 0) (10 5.1473315514 54.0850281573) (40 . 0.0000000000) (41 . 0.0000000000) (42 . 0.0000000000) (91 . 0) (10 4.9684461130 54.1744708764) (40 . 0.0000000000) (41 . 0.0000000000) (42 . -0.2840790438) (91 . 0) (10 4.8578888320 54.3533563146) (40 . 0.0000000000) (41 . 0.0000000000) (42 . 0.0000000000) (91 . 0) (10 4.8578888320 58.7978505647) (40 . 0.0000000000) (41 . 0.0000000000) (42 . -0.2849552788) (91 . 0) (10 5.1357332806 59.2457868447) (40 . 0.0000000000) (41 . 0.0000000000) (42 . 0.0000000000) (91 . 0) (10 5.7059533194 59.5285894504) (40 . 0.0000000000) (41 . 0.0000000000) (42 . -0.5788431251) (91 . 0) (10 6.4578888321 59.0967000000) (40 . 0.0000000000) (41 . 0.0000000000) (42 . 0.0000000000) (91 . 0) (10 6.4578888321 56.5967000000) (40 . 0.0000000000) (41 . 0.0000000000) (42 . 0.4142135624) (91 . 0) (10 6.6578888323 56.3967000000) (40 . 0.0000000000) (41 . 0.0000000000) (42 . 0.0000000000) (91 . 0) (10 7.6578888323 56.3967000000) (40 . 0.0000000000) (41 . 0.0000000000) (42 . 0.4142135624) (91 . 0) (10 7.8578888320 56.5967000000) (40 . 0.0000000000) (41 . 0.0000000000) (42 . 0.0000000000) (91 . 0) (10 7.8578888320 68.1967000000) (40 . 0.0000000000) (41 . 0.0000000000) (42 . 0.4142135624) (91 . 0) (10 7.6578888323 68.3967000000) (40 . 0.0000000000) (41 . 0.0000000000) (42 . 0.0000000000) (91 . 0) (10 6.0454832279 68.3966999999) (40 . 0.0000000000) (41 . 0.0000000000) (42 . 0.2102297862) (91 . 0) (10 5.8980524000 68.3318449257) (40 . 0.0000000000) (41 . 0.0000000000) (42 . 0.0000000000) (91 . 0) (10 4.9100720566 67.2540481876) (40 . 0.0000000000) (41 . 0.0000000000) (42 . 0.1876437528) (91 . 0) (10 4.8575028848 67.1189032619) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 80) (70 . 1) (43 . 0.0000000000) (38 . 0.0000000000) (39 . 0.0000000000) (10 -20.9421111602 72.8967000000) (40 . 0.0000000000) (41 . 0.0000000000) (42 . 0.4142135624) (91 . 0) (10 -21.4421111602 73.3967000000) (40 . 0.0000000000) (41 . 0.0000000000) (42 . 0.0000000000) (91 . 0) (10 -28.0421111602 73.3967000000) (40 . 0.0000000000) (41 . 0.0000000000) (42 . -0.4142135624) (91 . 0) (10 -28.5421111602 73.8967000000) (40 . 0.0000000000) (41 . 0.0000000000) (42 . 0.0000000000) (91 . 0) (10 -28.5421111602 77.8967000000) (40 . 0.0000000000) (41 . 0.0000000000) (42 . 0.4142135624) (91 . 0) (10 -29.0421111602 78.3967000000) (40 . 0.0000000000) (41 . 0.0000000000) (42 . 0.0000000000) (91 . 0) (10 -29.3405054536 78.3967000000) (40 . 0.0000000000) (41 . 0.0000000000) (42 . 0.3152987889) (91 . 0) (10 -29.8103517640 78.0677100716) (40 . 0.0000000000) (41 . 0.0000000000) (42 . 0.0000000000) (91 . 0) (10 -30.4300496843 76.3651040286) (40 . 0.0000000000) (41 . 0.0000000000) (42 . 0.5205670506) (91 . 0) (10 -30.2421111602 76.0967000000) (40 . 0.0000000000) (41 . 0.0000000000) (42 . 0.0000000000) (91 . 0) (10 -30.0421111602 76.0967000000) (40 . 0.0000000000) (41 . 0.0000000000) (42 . -0.4142135624) (91 . 0) (10 -29.7421111602 75.7967000000) (40 . 0.0000000000) (41 . 0.0000000000) (42 . 0.0000000000) (91 . 0) (10 -29.7421111602 73.8967000000) (40 . 0.0000000000) (41 . 0.0000000000) (42 . -0.4142135624) (91 . 0) (10 -30.2421111602 73.3967000000) (40 . 0.0000000000) (41 . 0.0000000000) (42 . 0.0000000000) (91 . 0) (10 -30.4421111602 73.3967000000) (40 . 0.0000000000) (41 . 0.0000000000) (42 . 0.4142135624) (91 . 0) (10 -30.9421111602 72.8967000000) (40 . 0.0000000000) (41 . 0.0000000000) (42 . 0.0000000000) (91 . 0) (10 -30.9421111602 68.8967000000) (40 . 0.0000000000) (41 . 0.0000000000) (42 . 0.4142135624) (91 . 0) (10 -30.4421111602 68.3967000000) (40 . 0.0000000000) (41 . 0.0000000000) (42 . 0.0000000000) (91 . 0) (10 -27.6421111602 68.3967000000) (40 . 0.0000000000) (41 . 0.0000000000) (42 . 0.4142135624) (91 . 0) (10 -27.1421111602 68.8967000000) (40 . 0.0000000000) (41 . 0.0000000000) (42 . 0.0000000000) (91 . 0) (10 -27.1421111602 69.0967000000) (40 . 0.0000000000) (41 . 0.0000000000) (42 . 0.4142135624) (91 . 0) (10 -27.6421111602 69.5967000000) (40 . 0.0000000000) (41 . 0.0000000000) (42 . 0.0000000000) (91 . 0) (10 -28.0421111602 69.5967000000) (40 . 0.0000000000) (41 . 0.0000000000) (42 . -0.4142135624) (91 . 0) (10 -28.5421111602 70.0967000000) (40 . 0.0000000000) (41 . 0.0000000000) (42 . 0.0000000000) (91 . 0) (10 -28.5421111602 70.7967000000) (40 . 0.0000000000) (41 . 0.0000000000) (42 . -0.4142135624) (91 . 0) (10 -28.0421111602 71.2967000000) (40 . 0.0000000000) (41 . 0.0000000000) (42 . 0.0000000000) (91 . 0) (10 -23.8421111602 71.2967000000) (40 . 0.0000000000) (41 . 0.0000000000) (42 . -0.4142135624) (91 . 0) (10 -23.3421111602 70.7967000000) (40 . 0.0000000000) (41 . 0.0000000000) (42 . 0.0000000000) (91 . 0) (10 -23.3421111602 70.0967000000) (40 . 0.0000000000) (41 . 0.0000000000) (42 . -0.4142135624) (91 . 0) (10 -23.8421111602 69.5967000000) (40 . 0.0000000000) (41 . 0.0000000000) (42 . 0.0000000000) (91 . 0) (10 -24.2421111602 69.5967000000) (40 . 0.0000000000) (41 . 0.0000000000) (42 . 0.4142135624) (91 . 0) (10 -24.7421111602 69.0967000000) (40 . 0.0000000000) (41 . 0.0000000000) (42 . 0.0000000000) (91 . 0) (10 -24.7421111602 68.8967000000) (40 . 0.0000000000) (41 . 0.0000000000) (42 . 0.4142135624) (91 . 0) (10 -24.2421111602 68.3967000000) (40 . 0.0000000000) (41 . 0.0000000000) (42 . 0.0000000000) (91 . 0) (10 0.3578888398 68.3967000000) (40 . 0.0000000000) (41 . 0.0000000000) (42 . 0.0000000000) (91 . 0) (10 24.9578888398 68.3967000000) (40 . 0.0000000000) (41 . 0.0000000000) (42 . 0.4142135624) (91 . 0) (10 25.4578888398 68.8967000000) (40 . 0.0000000000) (41 . 0.0000000000) (42 . 0.0000000000) (91 . 0) (10 25.4578888398 69.0967000000) (40 . 0.0000000000) (41 . 0.0000000000) (42 . 0.4142135624) (91 . 0) (10 24.9578888398 69.5967000000) (40 . 0.0000000000) (41 . 0.0000000000) (42 . 0.0000000000) (91 . 0) (10 24.5578888398 69.5967000000) (40 . 0.0000000000) (41 . 0.0000000000) (42 . -0.4142135624) (91 . 0) (10 24.0578888398 70.0967000000) (40 . 0.0000000000) (41 . 0.0000000000) (42 . 0.0000000000) (91 . 0) (10 24.0578888398 70.7967000000) (40 . 0.0000000000) (41 . 0.0000000000) (42 . -0.4142135624) (91 . 0) (10 24.5578888398 71.2967000000) (40 . 0.0000000000) (41 . 0.0000000000) (42 . 0.0000000000) (91 . 0) (10 28.7578888398 71.2967000000) (40 . 0.0000000000) (41 . 0.0000000000) (42 . -0.4142135624) (91 . 0) (10 29.2578888398 70.7967000000) (40 . 0.0000000000) (41 . 0.0000000000) (42 . 0.0000000000) (91 . 0) (10 29.2578888398 70.0967000000) (40 . 0.0000000000) (41 . 0.0000000000) (42 . -0.4142135624) (91 . 0) (10 28.7578888398 69.5967000000) (40 . 0.0000000000) (41 . 0.0000000000) (42 . 0.0000000000) (91 . 0) (10 28.3578888398 69.5967000000) (40 . 0.0000000000) (41 . 0.0000000000) (42 . 0.4142135624) (91 . 0) (10 27.8578888398 69.0967000000) (40 . 0.0000000000) (41 . 0.0000000000) (42 . 0.0000000000) (91 . 0) (10 27.8578888398 68.8967000000) (40 . 0.0000000000) (41 . 0.0000000000) (42 . 0.4142135624) (91 . 0) (10 28.3578888398 68.3967000000) (40 . 0.0000000000) (41 . 0.0000000000) (42 . 0.0000000000) (91 . 0) (10 31.1578888398 68.3967000000) (40 . 0.0000000000) (41 . 0.0000000000) (42 . 0.4142135624) (91 . 0) (10 31.6578888398 68.8967000000) (40 . 0.0000000000) (41 . 0.0000000000) (42 . 0.0000000000) (91 . 0) (10 31.6578888398 72.8967000000) (40 . 0.0000000000) (41 . 0.0000000000) (42 . 0.4142135624) (91 . 0) (10 31.1578888398 73.3967000000) (40 . 0.0000000000) (41 . 0.0000000000) (42 . 0.0000000000) (91 . 0) (10 30.9578888398 73.3967000000) (40 . 0.0000000000) (41 . 0.0000000000) (42 . -0.4142135624) (91 . 0) (10 30.4578888398 73.8967000000) (40 . 0.0000000000) (41 . 0.0000000000) (42 . 0.0000000000) (91 . 0) (10 30.4578888398 75.7967000000) (40 . 0.0000000000) (41 . 0.0000000000) (42 . -0.4142135624) (91 . 0) (10 30.7578888398 76.0967000000) (40 . 0.0000000000) (41 . 0.0000000000) (42 . 0.0000000000) (91 . 0) (10 30.9578888398 76.0967000000) (40 . 0.0000000000) (41 . 0.0000000000) (42 . 0.5205670506) (91 . 0) (10 31.1458273640 76.3651040286) (40 . 0.0000000000) (41 . 0.0000000000) (42 . 0.0000000000) (91 . 0) (10 30.5261294436 78.0677100716) (40 . 0.0000000000) (41 . 0.0000000000) (42 . 0.3152987889) (91 . 0) (10 30.0562831332 78.3967000000) (40 . 0.0000000000) (41 . 0.0000000000) (42 . 0.0000000000) (91 . 0) (10 29.7578888398 78.3967000000) (40 . 0.0000000000) (41 . 0.0000000000) (42 . 0.4142135624) (91 . 0) (10 29.2578888398 77.8967000000) (40 . 0.0000000000) (41 . 0.0000000000) (42 . 0.0000000000) (91 . 0) (10 29.2578888398 73.8967000000) (40 . 0.0000000000) (41 . 0.0000000000) (42 . -0.4142135624) (91 . 0) (10 28.7578888398 73.3967000000) (40 . 0.0000000000) (41 . 0.0000000000) (42 . 0.0000000000) (91 . 0) (10 22.1578888398 73.3967000000) (40 . 0.0000000000) (41 . 0.0000000000) (42 . 0.4142135624) (91 . 0) (10 21.6578888398 72.8967000000) (40 . 0.0000000000) (41 . 0.0000000000) (42 . 0.0000000000) (91 . 0) (10 21.6578888398 71.8967000000) (40 . 0.0000000000) (41 . 0.0000000000) (42 . -0.4142135624) (91 . 0) (10 21.1578888398 71.3967000000) (40 . 0.0000000000) (41 . 0.0000000000) (42 . 0.0000000000) (91 . 0) (10 1.0235742648 71.3967000000) (40 . 0.0000000000) (41 . 0.0000000000) (42 . 0.1989123674) (91 . 0) (10 0.8821529085 71.3381213562) (40 . 0.0000000000) (41 . 0.0000000000) (42 . 0.0000000000) (91 . 0) (10 0.4993101960 70.9552786438) (40 . 0.0000000000) (41 . 0.0000000000) (42 . -0.1989123674) (91 . 0) (10 0.3578888398 70.8967000000) (40 . 0.0000000000) (41 . 0.0000000000) (42 . -0.1989123674) (91 . 0) (10 0.2164674836 70.9552786438) (40 . 0.0000000000) (41 . 0.0000000000) (42 . 0.0000000000) (91 . 0) (10 -0.1663752289 71.3381213562) (40 . 0.0000000000) (41 . 0.0000000000) (42 . 0.1989123674) (91 . 0) (10 -0.3077965851 71.3967000000) (40 . 0.0000000000) (41 . 0.0000000000) (42 . 0.0000000000) (91 . 0) (10 -20.4421111602 71.3967000000) (40 . 0.0000000000) (41 . 0.0000000000) (42 . -0.4142135624) (91 . 0) (10 -20.9421111602 71.8967000000) (40 . 0.0000000000) (41 . 0.0000000000) (42 . 0.0000000000) (91 . 0) (210 0.0000000000 0.0000000000 1.0000000000))
((0 . "LWPOLYLINE") (100 . "AcDbEntity") (67 . 0) (8 . "A-Window") (62 . 3) (6 . "Continuous") (100 . "AcDbPolyline") (90 . 44) (70 . 1) (43 . 0.0000000000) (38 . 0.0000000000) (39 . 0.0000000000) (10 23.6421111610 70.2966877930) (40 . 0.0000000000) (41 . 0.0000000000) (42 . 0.0000000000) (91 . 0) (10 23.6421111610 70.0967122070) (40 . 0.0000000000) (41 . 0.0000000000) (42 . 0.4142225008) (91 . 0) (10 24.0421111608 69.6967000000) (40 . 0.0000000000) (41 . 0.0000000000) (42 . 0.0000000000) (91 . 0) (10 24.2421111608 69.6967000000) (40 . 0.0000000000) (41 . 0.0000000000) (42 . -0.4142135624) (91 . 0) (10 24.8421111608 69.0967000000) (40 . 0.0000000000) (41 . 0.0000000000) (42 . 0.0000000000) (91 . 0) (10 24.8421111608 68.8967000000) (40 . 0.0000000000) (41 . 0.0000000000) (42 . -0.2513806714) (91 . 0) (10 24.5737736398 68.3967000000) (40 . 0.0000000000) (41 . 0.0000000000) (42 . 0.0000000000) (91 . 0) (10 22.8419369362 68.3967000000) (40 . 0.0000000000) (41 . 0.0000000000) (42 . 0.4142135624) (91 . 0) (10 22.3419369362 67.8967000000) (40 . 0.0000000000) (41 . 0.0000000000) (42 . 0.0000000000) (91 . 0) (10 22.3419369362 63.2967000000) (40 . 0.0000000000) (41 . 0.0000000000) (42 . 0.4142135624) (91 . 0) (10 22.8419369362 62.7967000000) (40 . 0.0000000000) (41 . 0.0000000000) (42 . 0.0000000000) (91 . 0) (10 23.0521408922 62.7967000000) (40 . 0.0000000000) (41 . 0.0000000000) (42 . 0.0000000000) (91 . 0) (10 23.1968257876 63.1989988506) (40 . 0.0000000000) (41 . 0.0000000000) (42 . 0.0000000000) (91 . 0) (10 23.5540632006 63.1989988506) (40 . 0.0000000000) (41 . 0.0000000000) (42 . 0.0000000000) (91 . 0) (10 23.6938075589 62.7967000000) (40 . 0.0000000000) (41 . 0.0000000000) (42 . 0.0000000000) (91 . 0) (10 24.3354742255 62.7967000000) (40 . 0.0000000000) (41 . 0.0000000000) (42 . 0.0000000000) (91 . 0) (10 24.4801591210 63.1989988506) (40 . 0.0000000000) (41 . 0.0000000000) (42 . 0.0000000000) (91 . 0) (10 24.8373965339 63.1989988506) (40 . 0.0000000000) (41 . 0.0000000000) (42 . 0.0000000000) (91 . 0) (10 24.9771408922 62.7967000000) (40 . 0.0000000000) (41 . 0.0000000000) (42 . 0.0000000000) (91 . 0) (10 25.6188075589 62.7967000000) (40 . 0.0000000000) (41 . 0.0000000000) (42 . 0.0000000000) (91 . 0) (10 25.7634924543 63.1989988506) (40 . 0.0000000000) (41 . 0.0000000000) (42 . 0.0000000000) (91 . 0) (10 26.1207298673 63.1989988506) (40 . 0.0000000000) (41 . 0.0000000000) (42 . 0.0000000000) (91 . 0) (10 26.2604742255 62.7967000000) (40 . 0.0000000000) (41 . 0.0000000000) (42 . 0.0000000000) (91 . 0) (10 26.9021408922 62.7967000000) (40 . 0.0000000000) (41 . 0.0000000000) (42 . 0.0000000000) (91 . 0) (10 27.0468257876 63.1989988506) (40 . 0.0000000000) (41 . 0.0000000000) (42 . 0.0000000000) (91 . 0) (10 27.4040632006 63.1989988506) (40 . 0.0000000000) (41 . 0.0000000000) (42 . 0.0000000000) (91 . 0) (10 27.5438075589 62.7967000000) (40 . 0.0000000000) (41 . 0.0000000000) (42 . 0.0000000000) (91 . 0) (10 28.1854742255 62.7967000000) (40 . 0.0000000000) (41 . 0.0000000000) (42 . 0.0000000000) (91 . 0) (10 28.3301591210 63.1989988506) (40 . 0.0000000000) (41 . 0.0000000000) (42 . 0.0000000000) (91 . 0) (10 28.6873965339 63.1989988506) (40 . 0.0000000000) (41 . 0.0000000000) (42 . 0.0000000000) (91 . 0) (10 28.8271408922 62.7967000000) (40 . 0.0000000000) (41 . 0.0000000000) (42 . 0.0000000000) (91 . 0) (10 29.0419369361 62.7967000000) (40 . 0.0000000000) (41 . 0.0000000000) (42 . 0.4142135624) (91 . 0) (10 29.5419369361 63.2967000000) (40 . 0.0000000000) (41 . 0.0000000000) (42 . 0.0000000000) (91 . 0) (10 29.5419369361 67.8967000000) (40 . 0.0000000000) (41 . 0.0000000000) (42 . 0.4142135624) (91 . 0) (10 29.0419369361 68.3967000000) (40 . 0.0000000000) (41 . 0.0000000000) (42 . 0.0000000000) (91 . 0) (10 27.3104486818 68.3967000000) (40 . 0.0000000000) (41 . 0.0000000000) (42 . -0.2513806714) (91 . 0) (10 27.0421111608 68.8967000000) (40 . 0.0000000000) (41 . 0.0000000000) (42 . 0.0000000000) (91 . 0) (10 27.0421111608 69.0967000000) (40 . 0.0000000000) (41 . 0.0000000000) (42 . -0.4142135624) (91 . 0) (10 27.6421111608 69.6967000000) (40 . 0.0000000000) (41 . 0.0000000000) (42 . 0.0000000000) (91 . 0) (10 27.8421111608 69.6967000000) (40 . 0.0000000000) (41 . 0.0000000000) (42 . 0.4142135624) (91 . 0) (10 28.2421111608 70.0967000000) (40 . 0.0000000000) (41 . 0.0000000000) (42 . 0.0000000000) (91 . 0) (10 28.2421111608 70.2967000000) (40 . 0.0000000000) (41 . 0.0000000000) (42 . 0.4142135624) (91 . 0) (10 27.8421111608 70.6967000000) (40 . 0.0000000000) (41 . 0.0000000000) (42 . 0.0000000000) (91 . 0) (10 24.0421111608 70.6967000000) (40 . 0.0000000000) (41 . 0.0000000000) (42 . 0.4142225008) (91 . 0) (210 0.0000000000 0.0000000000 -1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 28.0969369362 67.3467000000) (40 . 0.0000000000) (41 . 0.0000000000) (42 . 0.0000000000) (91 . 0) (10 28.0969369362 64.2467000000) (40 . 0.0000000000) (41 . 0.0000000000) (42 . 0.0000000000) (91 . 0) (10 26.5969369362 64.2467000000) (40 . 0.0000000000) (41 . 0.0000000000) (42 . 0.0000000000) (91 . 0) (10 26.5969369362 67.3467000000) (40 . 0.0000000000) (41 . 0.0000000000) (42 . 0.0000000000) (91 . 0) (210 0.0000000000 0.0000000000 -1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 25.2469369362 67.3467000000) (40 . 0.0000000000) (41 . 0.0000000000) (42 . 0.0000000000) (91 . 0) (10 25.2469369362 64.2467000000) (40 . 0.0000000000) (41 . 0.0000000000) (42 . 0.0000000000) (91 . 0) (10 23.7469369362 64.2467000000) (40 . 0.0000000000) (41 . 0.0000000000) (42 . 0.0000000000) (91 . 0) (10 23.7469369362 67.3467000000) (40 . 0.0000000000) (41 . 0.0000000000) (42 . 0.0000000000) (91 . 0) (210 0.0000000000 0.0000000000 -1.0000000000))
((0 . "LWPOLYLINE") (100 . "AcDbEntity") (67 . 0) (8 . "A-Window") (62 . 151) (6 . "Continuous") (100 . "AcDbPolyline") (90 . 44) (70 . 1) (43 . 0.0000000000) (38 . 0.0000000000) (39 . 0.0000000000) (10 31.6578888398 91.8967000000) (40 . 0.0000000000) (41 . 0.0000000000) (42 . 0.0000000000) (91 . 0) (10 31.6578888398 80.7967000000) (40 . 0.0000000000) (41 . 0.0000000000) (42 . -0.4142135624) (91 . 0) (10 31.1578888398 80.2967000000) (40 . 0.0000000000) (41 . 0.0000000000) (42 . 0.0000000000) (91 . 0) (10 29.1578888398 80.2967000000) (40 . 0.0000000000) (41 . 0.0000000000) (42 . 0.4142135624) (91 . 0) (10 28.6578888398 79.7967000000) (40 . 0.0000000000) (41 . 0.0000000000) (42 . 0.0000000000) (91 . 0) (10 28.6578888398 79.5967000000) (40 . 0.0000000000) (41 . 0.0000000000) (42 . 0.4142135624) (91 . 0) (10 29.1578888398 79.0967000000) (40 . 0.0000000000) (41 . 0.0000000000) (42 . 0.0000000000) (91 . 0) (10 31.1578888398 79.0967000000) (40 . 0.0000000000) (41 . 0.0000000000) (42 . -0.4142135624) (91 . 0) (10 31.6578888398 78.5967000000) (40 . 0.0000000000) (41 . 0.0000000000) (42 . 0.0000000000) (91 . 0) (10 31.6578888398 76.2967000000) (40 . 0.0000000000) (41 . 0.0000000000) (42 . -0.4142135624) (91 . 0) (10 31.4578888398 76.0967000000) (40 . 0.0000000000) (41 . 0.0000000000) (42 . 0.0000000000) (91 . 0) (10 30.7757356338 76.0967000000) (40 . 0.0000000000) (41 . 0.0000000000) (42 . 0.5522631265) (91 . 0) (10 30.5954310223 75.8101537865) (40 . 0.0000000000) (41 . 0.0000000000) (42 . 0.0000000000) (91 . 0) (10 31.6381934513 73.6377320594) (40 . 0.0000000000) (41 . 0.0000000000) (42 . -0.1123491485) (91 . 0) (10 31.6578888398 73.5511858458) (40 . 0.0000000000) (41 . 0.0000000000) (42 . 0.0000000000) (91 . 0) (10 31.6578888398 67.1967000000) (40 . 0.0000000000) (41 . 0.0000000000) (42 . 0.4142135624) (91 . 0) (10 32.2578888398 66.5967000000) (40 . 0.0000000000) (41 . 0.0000000000) (42 . 0.4142135624) (91 . 0) (10 32.8578888398 67.1967000000) (40 . 0.0000000000) (41 . 0.0000000000) (42 . 0.0000000000) (91 . 0) (10 32.8578888398 93.0967000000) (40 . 0.0000000000) (41 . 0.0000000000) (42 . 0.4142135624) (91 . 0) (10 32.3578888398 93.5967000000) (40 . 0.0000000000) (41 . 0.0000000000) (42 . 0.0000000000) (91 . 0) (10 0.3578888398 93.5967000000) (40 . 0.0000000000) (41 . 0.0000000000) (42 . 0.0000000000) (91 . 0) (10 -31.6421111602 93.5967000000) (40 . 0.0000000000) (41 . 0.0000000000) (42 . 0.4142135624) (91 . 0) (10 -32.1421111602 93.0967000000) (40 . 0.0000000000) (41 . 0.0000000000) (42 . 0.0000000000) (91 . 0) (10 -32.1421111602 67.1967000000) (40 . 0.0000000000) (41 . 0.0000000000) (42 . 0.4142135624) (91 . 0) (10 -31.5421111602 66.5967000000) (40 . 0.0000000000) (41 . 0.0000000000) (42 . 0.4142135624) (91 . 0) (10 -30.9421111602 67.1967000000) (40 . 0.0000000000) (41 . 0.0000000000) (42 . 0.0000000000) (91 . 0) (10 -30.9421111602 73.5511858458) (40 . 0.0000000000) (41 . 0.0000000000) (42 . -0.1123491485) (91 . 0) (10 -30.9224157717 73.6377320594) (40 . 0.0000000000) (41 . 0.0000000000) (42 . 0.0000000000) (91 . 0) (10 -29.8796533427 75.8101537865) (40 . 0.0000000000) (41 . 0.0000000000) (42 . 0.5522631265) (91 . 0) (10 -30.0599579542 76.0967000000) (40 . 0.0000000000) (41 . 0.0000000000) (42 . 0.0000000000) (91 . 0) (10 -30.7421111602 76.0967000000) (40 . 0.0000000000) (41 . 0.0000000000) (42 . -0.4142135624) (91 . 0) (10 -30.9421111602 76.2967000000) (40 . 0.0000000000) (41 . 0.0000000000) (42 . 0.0000000000) (91 . 0) (10 -30.9421111602 78.5967000000) (40 . 0.0000000000) (41 . 0.0000000000) (42 . -0.4142135624) (91 . 0) (10 -30.4421111602 79.0967000000) (40 . 0.0000000000) (41 . 0.0000000000) (42 . 0.0000000000) (91 . 0) (10 -28.4421111602 79.0967000000) (40 . 0.0000000000) (41 . 0.0000000000) (42 . 0.4142135624) (91 . 0) (10 -27.9421111602 79.5967000000) (40 . 0.0000000000) (41 . 0.0000000000) (42 . 0.0000000000) (91 . 0) (10 -27.9421111602 79.7967000000) (40 . 0.0000000000) (41 . 0.0000000000) (42 . 0.4142135624) (91 . 0) (10 -28.4421111602 80.2967000000) (40 . 0.0000000000) (41 . 0.0000000000) (42 . 0.0000000000) (91 . 0) (10 -30.4421111602 80.2967000000) (40 . 0.0000000000) (41 . 0.0000000000) (42 . -0.4142135624) (91 . 0) (10 -30.9421111602 80.7967000000) (40 . 0.0000000000) (41 . 0.0000000000) (42 . 0.0000000000) (91 . 0) (10 -30.9421111602 91.8967000000) (40 . 0.0000000000) (41 . 0.0000000000) (42 . -0.4142135624) (91 . 0) (10 -30.4421111602 92.3967000000) (40 . 0.0000000000) (41 . 0.0000000000) (42 . 0.0000000000) (91 . 0) (10 0.3578888398 92.3967000000) (40 . 0.0000000000) (41 . 0.0000000000) (42 . 0.0000000000) (91 . 0) (10 31.1578888398 92.3967000000) (40 . 0.0000000000) (41 . 0.0000000000) (42 . -0.4142135624) (91 . 0) (210 0.0000000000 0.0000000000 1.0000000000))
((0 . "LINE") (100 . "AcDbEntity") (67 . 0) (8 . "A-Window") (62 . 151) (6 . "Continuous") (100 . "AcDbLine") (10 2.5828888395 59.8994120805 0.0000000000) (11 2.5828888395 60.7929549452 0.0000000000) (210 0.0000000000 0.0000000000 1.0000000000))
((0 . "LINE") (100 . "AcDbEntity") (67 . 0) (8 . "A-Window") (62 . 151) (6 . "Continuous") (100 . "AcDbLine") (10 2.5828888395 61.5694120805 0.0000000000) (11 2.5828888395 62.4629549452 0.0000000000) (210 0.0000000000 0.0000000000 1.0000000000))
((0 . "LINE") (100 . "AcDbEntity") (67 . 0) (8 . "A-Window") (62 . 151) (6 . "Continuous") (100 . "AcDbLine") (10 2.5828888395 56.5594120805 0.0000000000) (11 2.5828888395 57.4529549452 0.0000000000) (210 0.0000000000 0.0000000000 1.0000000000))
((0 . "LINE") (100 . "AcDbEntity") (67 . 0) (8 . "A-Window") (62 . 151) (6 . "Continuous") (100 . "AcDbLine") (10 2.5828888395 58.2294120805 0.0000000000) (11 2.5828888395 59.1229549452 0.0000000000) (210 0.0000000000 0.0000000000 1.0000000000))
((0 . "LINE") (100 . "AcDbEntity") (67 . 0) (8 . "A-Window") (62 . 151) (6 . "Continuous") (100 . "AcDbLine") (10 -1.8671111605 55.5896136866 0.0000000000) (11 -1.8671111605 56.4831565513 0.0000000000) (210 0.0000000000 0.0000000000 1.0000000000))
((0 . "LINE") (100 . "AcDbEntity") (67 . 0) (8 . "A-Window") (62 . 151) (6 . "Continuous") (100 . "AcDbLine") (10 -1.8671111605 57.2596136866 0.0000000000) (11 -1.8671111605 58.1531565513 0.0000000000) (210 0.0000000000 0.0000000000 1.0000000000))
((0 . "LINE") (100 . "AcDbEntity") (67 . 0) (8 . "A-Window") (62 . 151) (6 . "Continuous") (100 . "AcDbLine") (10 -1.8671111605 58.9296136866 0.0000000000) (11 -1.8671111605 59.8231565513 0.0000000000) (210 0.0000000000 0.0000000000 1.0000000000))
((0 . "LINE") (100 . "AcDbEntity") (67 . 0) (8 . "A-Window") (62 . 151) (6 . "Continuous") (100 . "AcDbLine") (10 -1.8671111605 60.5996136866 0.0000000000) (11 -1.8671111605 61.4931565513 0.0000000000) (210 0.0000000000 0.0000000000 1.0000000000))
((0 . "LINE") (100 . "AcDbEntity") (67 . 0) (8 . "A-Window") (62 . 151) (6 . "Continuous") (100 . "AcDbLine") (10 -1.8671111605 62.2696136866 0.0000000000) (11 -1.8671111605 63.1631565513 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 57.2596136866) (40 . 0.0000000000) (41 . 0.0000000000) (42 . 0.0000000000) (91 . 0) (10 -2.3921111605 56.8713851190) (40 . 0.0000000000) (41 . 0.0000000000) (42 . 0.0000000000) (91 . 0) (10 -1.8671111605 56.4831565513) (40 . 0.0000000000) (41 . 0.0000000000) (42 . 0.0000000000) (91 . 0) (10 2.5828888395 57.4529549452) (40 . 0.0000000000) (41 . 0.0000000000) (42 . 0.0000000000) (91 . 0) (10 3.1078888395 57.8411835129) (40 . 0.0000000000) (41 . 0.0000000000) (42 . 0.0000000000) (91 . 0) (10 2.5828888395 58.2294120805) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 60.5996136866) (40 . 0.0000000000) (41 . 0.0000000000) (42 . 0.0000000000) (91 . 0) (10 -2.3921111605 60.2113851190) (40 . 0.0000000000) (41 . 0.0000000000) (42 . 0.0000000000) (91 . 0) (10 -1.8671111605 59.8231565513) (40 . 0.0000000000) (41 . 0.0000000000) (42 . 0.0000000000) (91 . 0) (10 2.5828888395 60.7929549452) (40 . 0.0000000000) (41 . 0.0000000000) (42 . 0.0000000000) (91 . 0) (10 3.1078888395 61.1811835129) (40 . 0.0000000000) (41 . 0.0000000000) (42 . 0.0000000000) (91 . 0) (10 2.5828888395 61.5694120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 3.1078888395 59.5111835129 0.0000000000) (11 -2.3921111605 58.5413851190 0.0000000000) (210 0.0000000000 0.0000000000 1.0000000000))
((0 . "LINE") (100 . "AcDbEntity") (67 . 0) (8 . "A-Window") (62 . 151) (6 . "Continuous") (100 . "AcDbLine") (10 3.1078888395 61.1811835129 0.0000000000) (11 -2.3921111605 60.2113851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 58.9296136866) (40 . 0.0000000000) (41 . 0.0000000000) (42 . 0.0000000000) (91 . 0) (10 -2.3921111605 58.5413851190) (40 . 0.0000000000) (41 . 0.0000000000) (42 . 0.0000000000) (91 . 0) (10 -1.8671111605 58.1531565513) (40 . 0.0000000000) (41 . 0.0000000000) (42 . 0.0000000000) (91 . 0) (10 2.5828888395 59.1229549452) (40 . 0.0000000000) (41 . 0.0000000000) (42 . 0.0000000000) (91 . 0) (10 3.1078888395 59.5111835129) (40 . 0.0000000000) (41 . 0.0000000000) (42 . 0.0000000000) (91 . 0) (10 2.5828888395 59.8994120805) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 62.2696136866) (40 . 0.0000000000) (41 . 0.0000000000) (42 . 0.0000000000) (91 . 0) (10 -2.3921111605 61.8813851190) (40 . 0.0000000000) (41 . 0.0000000000) (42 . 0.0000000000) (91 . 0) (10 -1.8671111605 61.4931565513) (40 . 0.0000000000) (41 . 0.0000000000) (42 . 0.0000000000) (91 . 0) (10 2.5828888395 62.4629549452) (40 . 0.0000000000) (41 . 0.0000000000) (42 . 0.0000000000) (91 . 0) (10 3.1078888395 62.8511835129) (40 . 0.0000000000) (41 . 0.0000000000) (42 . 0.0000000000) (91 . 0) (10 2.5828888395 63.2394120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 3.1078888395 62.8511835129 0.0000000000) (11 -2.3921111605 61.8813851190 0.0000000000) (210 0.0000000000 0.0000000000 1.0000000000))
((0 . "LINE") (100 . "AcDbEntity") (67 . 0) (8 . "A-Window") (62 . 151) (6 . "Continuous") (100 . "AcDbLine") (10 3.1078888395 57.8411835129 0.0000000000) (11 -2.3921111605 56.8713851190 0.0000000000) (210 0.0000000000 0.0000000000 1.0000000000))
((0 . "LINE") (100 . "AcDbEntity") (67 . 0) (8 . "A-Window") (62 . 151) (6 . "Continuous") (100 . "AcDbLine") (10 2.5828888395 66.9194120805 0.0000000000) (11 2.5828888395 67.8129549452 0.0000000000) (210 0.0000000000 0.0000000000 1.0000000000))
((0 . "LINE") (100 . "AcDbEntity") (67 . 0) (8 . "A-Window") (62 . 151) (6 . "Continuous") (100 . "AcDbLine") (10 2.5828888395 61.9094120805 0.0000000000) (11 2.5828888395 62.8029549452 0.0000000000) (210 0.0000000000 0.0000000000 1.0000000000))
((0 . "LINE") (100 . "AcDbEntity") (67 . 0) (8 . "A-Window") (62 . 151) (6 . "Continuous") (100 . "AcDbLine") (10 2.5828888395 63.5794120805 0.0000000000) (11 2.5828888395 64.4729549452 0.0000000000) (210 0.0000000000 0.0000000000 1.0000000000))
((0 . "LINE") (100 . "AcDbEntity") (67 . 0) (8 . "A-Window") (62 . 151) (6 . "Continuous") (100 . "AcDbLine") (10 2.5828888395 65.2494120805 0.0000000000) (11 2.5828888395 66.1429549452 0.0000000000) (210 0.0000000000 0.0000000000 1.0000000000))
((0 . "LINE") (100 . "AcDbEntity") (67 . 0) (8 . "A-Window") (62 . 151) (6 . "Continuous") (100 . "AcDbLine") (10 2.5828888395 71.9294120805 0.0000000000) (11 2.5828888395 72.8229549452 0.0000000000) (210 0.0000000000 0.0000000000 1.0000000000))
((0 . "LINE") (100 . "AcDbEntity") (67 . 0) (8 . "A-Window") (62 . 151) (6 . "Continuous") (100 . "AcDbLine") (10 2.5828888395 70.2594120805 0.0000000000) (11 2.5828888395 71.1529549452 0.0000000000) (210 0.0000000000 0.0000000000 1.0000000000))
((0 . "LINE") (100 . "AcDbEntity") (67 . 0) (8 . "A-Window") (62 . 151) (6 . "Continuous") (100 . "AcDbLine") (10 2.5828888395 68.5894120805 0.0000000000) (11 2.5828888395 69.4829549452 0.0000000000) (210 0.0000000000 0.0000000000 1.0000000000))
((0 . "LINE") (100 . "AcDbEntity") (67 . 0) (8 . "A-Window") (62 . 151) (6 . "Continuous") (100 . "AcDbLine") (10 -1.8671111605 60.9396136866 0.0000000000) (11 -1.8671111605 61.8331565513 0.0000000000) (210 0.0000000000 0.0000000000 1.0000000000))
((0 . "LINE") (100 . "AcDbEntity") (67 . 0) (8 . "A-Window") (62 . 151) (6 . "Continuous") (100 . "AcDbLine") (10 -1.8671111605 65.9496136866 0.0000000000) (11 -1.8671111605 66.8431565513 0.0000000000) (210 0.0000000000 0.0000000000 1.0000000000))
((0 . "LINE") (100 . "AcDbEntity") (67 . 0) (8 . "A-Window") (62 . 151) (6 . "Continuous") (100 . "AcDbLine") (10 -1.8671111605 67.6196136866 0.0000000000) (11 -1.8671111605 68.5131565513 0.0000000000) (210 0.0000000000 0.0000000000 1.0000000000))
((0 . "LINE") (100 . "AcDbEntity") (67 . 0) (8 . "A-Window") (62 . 151) (6 . "Continuous") (100 . "AcDbLine") (10 -1.8671111605 62.6096136866 0.0000000000) (11 -1.8671111605 63.5031565513 0.0000000000) (210 0.0000000000 0.0000000000 1.0000000000))
((0 . "LINE") (100 . "AcDbEntity") (67 . 0) (8 . "A-Window") (62 . 151) (6 . "Continuous") (100 . "AcDbLine") (10 -1.8671111605 64.2796136866 0.0000000000) (11 -1.8671111605 65.1731565513 0.0000000000) (210 0.0000000000 0.0000000000 1.0000000000))
((0 . "LINE") (100 . "AcDbEntity") (67 . 0) (8 . "A-Window") (62 . 151) (6 . "Continuous") (100 . "AcDbLine") (10 -1.8671111605 69.2896136866 0.0000000000) (11 -1.8671111605 70.1831565513 0.0000000000) (210 0.0000000000 0.0000000000 1.0000000000))
((0 . "LINE") (100 . "AcDbEntity") (67 . 0) (8 . "A-Window") (62 . 151) (6 . "Continuous") (100 . "AcDbLine") (10 -1.8671111605 70.9596136866 0.0000000000) (11 -1.8671111605 71.8531565513 0.0000000000) (210 0.0000000000 0.0000000000 1.0000000000))
((0 . "LINE") (100 . "AcDbEntity") (67 . 0) (8 . "A-Window") (62 . 151) (6 . "Continuous") (100 . "AcDbLine") (10 -1.8671111605 72.6296136866 0.0000000000) (11 -1.8671111605 72.8917774718 0.0000000000) (210 0.0000000000 0.0000000000 1.0000000000))
((0 . "LINE") (100 . "AcDbEntity") (67 . 0) (8 . "A-Window") (62 . 151) (6 . "Continuous") (100 . "AcDbLine") (10 3.1078888395 63.1911835129 0.0000000000) (11 -2.3921111605 62.2213851189 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 62.6096136866) (40 . 0.0000000000) (41 . 0.0000000000) (42 . 0.0000000000) (91 . 0) (10 -2.3921111605 62.2213851189) (40 . 0.0000000000) (41 . 0.0000000000) (42 . 0.0000000000) (91 . 0) (10 -1.8671111605 61.8331565513) (40 . 0.0000000000) (41 . 0.0000000000) (42 . 0.0000000000) (91 . 0) (10 2.5828888395 62.8029549452) (40 . 0.0000000000) (41 . 0.0000000000) (42 . 0.0000000000) (91 . 0) (10 3.1078888395 63.1911835129) (40 . 0.0000000000) (41 . 0.0000000000) (42 . 0.0000000000) (91 . 0) (10 2.5828888395 63.5794120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 3.1078888395 64.8611835129 0.0000000000) (11 -2.3921111605 63.8913851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 64.2796136866) (40 . 0.0000000000) (41 . 0.0000000000) (42 . 0.0000000000) (91 . 0) (10 -2.3921111605 63.8913851190) (40 . 0.0000000000) (41 . 0.0000000000) (42 . 0.0000000000) (91 . 0) (10 -1.8671111605 63.5031565513) (40 . 0.0000000000) (41 . 0.0000000000) (42 . 0.0000000000) (91 . 0) (10 2.5828888395 64.4729549452) (40 . 0.0000000000) (41 . 0.0000000000) (42 . 0.0000000000) (91 . 0) (10 3.1078888395 64.8611835129) (40 . 0.0000000000) (41 . 0.0000000000) (42 . 0.0000000000) (91 . 0) (10 2.5828888395 65.2494120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 3.1078888395 66.5311835129 0.0000000000) (11 -2.3921111605 65.5613851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 65.9496136866) (40 . 0.0000000000) (41 . 0.0000000000) (42 . 0.0000000000) (91 . 0) (10 -2.3921111605 65.5613851190) (40 . 0.0000000000) (41 . 0.0000000000) (42 . 0.0000000000) (91 . 0) (10 -1.8671111605 65.1731565513) (40 . 0.0000000000) (41 . 0.0000000000) (42 . 0.0000000000) (91 . 0) (10 2.5828888395 66.1429549452) (40 . 0.0000000000) (41 . 0.0000000000) (42 . 0.0000000000) (91 . 0) (10 3.1078888395 66.5311835129) (40 . 0.0000000000) (41 . 0.0000000000) (42 . 0.0000000000) (91 . 0) (10 2.5828888395 66.9194120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 3.1078888395 68.2011835129 0.0000000000) (11 -2.3921111605 67.2313851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 67.6196136866) (40 . 0.0000000000) (41 . 0.0000000000) (42 . 0.0000000000) (91 . 0) (10 -2.3921111605 67.2313851190) (40 . 0.0000000000) (41 . 0.0000000000) (42 . 0.0000000000) (91 . 0) (10 -1.8671111605 66.8431565513) (40 . 0.0000000000) (41 . 0.0000000000) (42 . 0.0000000000) (91 . 0) (10 2.5828888395 67.8129549452) (40 . 0.0000000000) (41 . 0.0000000000) (42 . 0.0000000000) (91 . 0) (10 3.1078888395 68.2011835129) (40 . 0.0000000000) (41 . 0.0000000000) (42 . 0.0000000000) (91 . 0) (10 2.5828888395 68.5894120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 3.1078888395 69.8711835129 0.0000000000) (11 -2.3921111605 68.9013851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 69.2896136866) (40 . 0.0000000000) (41 . 0.0000000000) (42 . 0.0000000000) (91 . 0) (10 -2.3921111605 68.9013851190) (40 . 0.0000000000) (41 . 0.0000000000) (42 . 0.0000000000) (91 . 0) (10 -1.8671111605 68.5131565513) (40 . 0.0000000000) (41 . 0.0000000000) (42 . 0.0000000000) (91 . 0) (10 2.5828888395 69.4829549452) (40 . 0.0000000000) (41 . 0.0000000000) (42 . 0.0000000000) (91 . 0) (10 3.1078888395 69.8711835129) (40 . 0.0000000000) (41 . 0.0000000000) (42 . 0.0000000000) (91 . 0) (10 2.5828888395 70.2594120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 3.1078888395 71.5411835129 0.0000000000) (11 -2.3921111605 70.5713851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 70.9596136866) (40 . 0.0000000000) (41 . 0.0000000000) (42 . 0.0000000000) (91 . 0) (10 -2.3921111605 70.5713851190) (40 . 0.0000000000) (41 . 0.0000000000) (42 . 0.0000000000) (91 . 0) (10 -1.8671111605 70.1831565513) (40 . 0.0000000000) (41 . 0.0000000000) (42 . 0.0000000000) (91 . 0) (10 2.5828888395 71.1529549452) (40 . 0.0000000000) (41 . 0.0000000000) (42 . 0.0000000000) (91 . 0) (10 3.1078888395 71.5411835129) (40 . 0.0000000000) (41 . 0.0000000000) (42 . 0.0000000000) (91 . 0) (10 2.5828888395 71.9294120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 1.2964471656 72.8917774718 0.0000000000) (11 -2.3921111605 72.2413851190 0.0000000000) (210 0.0000000000 0.0000000000 1.0000000000))
((0 . "LWPOLYLINE") (100 . "AcDbEntity") (67 . 0) (8 . "A-Window") (62 . 151) (6 . "Continuous") (100 . "AcDbPolyline") (90 . 6) (70 . 0) (43 . 0.0000000000) (38 . 0.0000000000) (39 . 0.0000000000) (10 -0.6641509873 72.8917774718) (40 . 0.0000000000) (41 . 0.0000000000) (42 . 0.0000000000) (91 . 0) (10 -1.8671111605 72.6296136866) (40 . 0.0000000000) (41 . 0.0000000000) (42 . 0.0000000000) (91 . 0) (10 -2.3921111605 72.2413851190) (40 . 0.0000000000) (41 . 0.0000000000) (42 . 0.0000000000) (91 . 0) (10 -1.8671111605 71.8531565513) (40 . 0.0000000000) (41 . 0.0000000000) (42 . 0.0000000000) (91 . 0) (10 2.5828888395 72.8229549452) (40 . 0.0000000000) (41 . 0.0000000000) (42 . 0.0000000000) (91 . 0) (10 2.6759572777 72.8917774718) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 4) (70 . 1) (43 . 0.0000000000) (38 . 0.0000000000) (39 . 0.0000000000) (10 5.8578888395 73.8917774718) (40 . 0.0000000000) (41 . 0.0000000000) (42 . 0.0000000000) (91 . 0) (10 5.8578888395 72.8917774718) (40 . 0.0000000000) (41 . 0.0000000000) (42 . 0.0000000000) (91 . 0) (10 -5.1421111605 72.8917774718) (40 . 0.0000000000) (41 . 0.0000000000) (42 . 0.0000000000) (91 . 0) (10 -5.1421111605 73.8917774718) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 3.1078888395 61.5211835128 0.0000000000) (11 -2.3921111605 63.5513851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 60.9396136866) (40 . 0.0000000000) (41 . 0.0000000000) (42 . 0.0000000000) (91 . 0) (10 -2.3921111605 63.5513851190) (40 . 0.0000000000) (41 . 0.0000000000) (42 . 0.0000000000) (91 . 0) (10 -1.8671111605 63.1631565513) (40 . 0.0000000000) (41 . 0.0000000000) (42 . 0.0000000000) (91 . 0) (10 2.5828888395 61.1329549452) (40 . 0.0000000000) (41 . 0.0000000000) (42 . 0.0000000000) (91 . 0) (10 3.1078888395 61.5211835128) (40 . 0.0000000000) (41 . 0.0000000000) (42 . 0.0000000000) (91 . 0) (10 2.5828888395 61.9094120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 2.5828888395 63.2394120805 0.0000000000) (11 2.5828888395 61.1329549452 0.0000000000) (210 0.0000000000 0.0000000000 1.0000000000))
((0 . "LINE") (100 . "AcDbEntity") (67 . 0) (8 . "A-Window") (62 . 151) (6 . "Continuous") (100 . "AcDbLine") (10 3.8219904546 78.2917774718 0.0000000000) (11 -3.1062127756 78.2917774718 0.0000000000) (210 0.0000000000 0.0000000000 1.0000000000))
((0 . "LINE") (100 . "AcDbEntity") (67 . 0) (8 . "A-Window") (62 . 151) (6 . "CENTER2") (100 . "AcDbLine") (10 0.3578888395 37.5451762388 0.0000000000) (11 0.3578888395 81.5869711621 0.0000000000) (210 0.0000000000 0.0000000000 1.0000000000))
((0 . "LINE") (100 . "AcDbEntity") (67 . 0) (8 . "A-Window") (62 . 151) (6 . "Continuous") (100 . "AcDbLine") (10 2.6672899163 77.2917774718 0.0000000000) (11 2.6672899163 73.8917774718 0.0000000000) (210 0.0000000000 0.0000000000 1.0000000000))
((0 . "LINE") (100 . "AcDbEntity") (67 . 0) (8 . "A-Window") (62 . 151) (6 . "Continuous") (100 . "AcDbLine") (10 -1.9515122373 77.2917774718 0.0000000000) (11 -1.9515122373 73.8917774718 0.0000000000) (210 0.0000000000 0.0000000000 1.0000000000))
((0 . "LWPOLYLINE") (100 . "AcDbEntity") (67 . 0) (8 . "A-Window") (62 . 151) (6 . "Continuous") (100 . "AcDbPolyline") (90 . 6) (70 . 0) (43 . 0.0000000000) (38 . 0.0000000000) (39 . 0.0000000000) (10 -4.2609133140 73.8917774718) (40 . 0.0000000000) (41 . 0.0000000000) (42 . 0.0000000000) (91 . 0) (10 -4.2609133140 77.2917774718) (40 . 0.0000000000) (41 . 0.0000000000) (42 . -0.8660254038) (91 . 0) (10 -1.9515122373 77.2917774718) (40 . 0.0000000000) (41 . 0.0000000000) (42 . -0.4330127019) (91 . 0) (10 2.6672899163 77.2917774718) (40 . 0.0000000000) (41 . 0.0000000000) (42 . -0.8660254038) (91 . 0) (10 4.9766909930 77.2917774718) (40 . 0.0000000000) (41 . 0.0000000000) (42 . 0.0000000000) (91 . 0) (10 4.9766909930 73.8917774718) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 4) (70 . 1) (43 . 0.0000000000) (38 . 0.0000000000) (39 . 0.0000000000) (10 2.5828888395 42.6957453328) (40 . 0.0000000000) (41 . 0.0000000000) (42 . 0.0000000000) (91 . 0) (10 0.9713231013 42.5675818646) (40 . 0.0000000000) (41 . 0.0000000000) (42 . 0.0000000000) (91 . 0) (10 2.5828888395 43.0839739004) (40 . 0.0000000000) (41 . 0.0000000000) (42 . 0.0000000000) (91 . 0) (10 2.7903888395 42.8898596166) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 2.7903888395 42.8898596166 0.0000000000) (11 0.9713231013 42.5675818646 0.0000000000) (210 0.0000000000 0.0000000000 1.0000000000))
((0 . "LINE") (100 . "AcDbEntity") (67 . 0) (8 . "A-Window") (62 . 151) (6 . "Continuous") (100 . "AcDbLine") (10 2.5828888395 48.2094120805 0.0000000000) (11 2.5828888395 49.1029549452 0.0000000000) (210 0.0000000000 0.0000000000 1.0000000000))
((0 . "LINE") (100 . "AcDbEntity") (67 . 0) (8 . "A-Window") (62 . 151) (6 . "Continuous") (100 . "AcDbLine") (10 2.5828888395 56.5594120805 0.0000000000) (11 2.5828888395 57.4529549452 0.0000000000) (210 0.0000000000 0.0000000000 1.0000000000))
((0 . "LINE") (100 . "AcDbEntity") (67 . 0) (8 . "A-Window") (62 . 151) (6 . "Continuous") (100 . "AcDbLine") (10 2.8941388395 44.5782406548 0.0000000000) (11 1.6210499782 44.3526917877 0.0000000000) (210 0.0000000000 0.0000000000 1.0000000000))
((0 . "LINE") (100 . "AcDbEntity") (67 . 0) (8 . "A-Window") (62 . 151) (6 . "Continuous") (100 . "AcDbLine") (10 2.5828888395 44.8694120805 0.0000000000) (11 2.5828888395 45.7629549452 0.0000000000) (210 0.0000000000 0.0000000000 1.0000000000))
((0 . "LWPOLYLINE") (100 . "AcDbEntity") (67 . 0) (8 . "A-Window") (62 . 151) (6 . "Continuous") (100 . "AcDbPolyline") (90 . 5) (70 . 0) (43 . 0.0000000000) (38 . 0.0000000000) (39 . 0.0000000000) (10 1.5110249293 44.0504004504) (40 . 0.0000000000) (41 . 0.0000000000) (42 . 0.0000000000) (91 . 0) (10 2.5828888395 44.2870692290) (40 . 0.0000000000) (41 . 0.0000000000) (42 . 0.0000000000) (91 . 0) (10 2.8941388395 44.5782406548) (40 . 0.0000000000) (41 . 0.0000000000) (42 . 0.0000000000) (91 . 0) (10 2.5828888395 44.8694120805) (40 . 0.0000000000) (41 . 0.0000000000) (42 . 0.0000000000) (91 . 0) (10 1.7415027540 44.6836330695) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 2.5828888395 46.5394120805 0.0000000000) (11 2.5828888395 47.4329549452 0.0000000000) (210 0.0000000000 0.0000000000 1.0000000000))
((0 . "LINE") (100 . "AcDbEntity") (67 . 0) (8 . "A-Window") (62 . 151) (6 . "Continuous") (100 . "AcDbLine") (10 2.5828888395 43.0839739004 0.0000000000) (11 2.5828888395 44.2870692290 0.0000000000) (210 0.0000000000 0.0000000000 1.0000000000))
((0 . "LINE") (100 . "AcDbEntity") (67 . 0) (8 . "A-Window") (62 . 151) (6 . "Continuous") (100 . "AcDbLine") (10 -1.8671111605 44.1620742983 0.0000000000) (11 -1.8671111605 44.7931565513 0.0000000000) (210 0.0000000000 0.0000000000 1.0000000000))
((0 . "LINE") (100 . "AcDbEntity") (67 . 0) (8 . "A-Window") (62 . 151) (6 . "Continuous") (100 . "AcDbLine") (10 -1.8671111605 45.5696136866 0.0000000000) (11 -1.8671111605 46.4631565513 0.0000000000) (210 0.0000000000 0.0000000000 1.0000000000))
((0 . "LINE") (100 . "AcDbEntity") (67 . 0) (8 . "A-Window") (62 . 151) (6 . "Continuous") (100 . "AcDbLine") (10 -1.8671111605 47.2396136866 0.0000000000) (11 -1.8671111605 48.1331565513 0.0000000000) (210 0.0000000000 0.0000000000 1.0000000000))
((0 . "LINE") (100 . "AcDbEntity") (67 . 0) (8 . "A-Window") (62 . 151) (6 . "Continuous") (100 . "AcDbLine") (10 -1.8671111605 57.2596136866 0.0000000000) (11 -1.8671111605 58.1531565513 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 45.5696136866) (40 . 0.0000000000) (41 . 0.0000000000) (42 . 0.0000000000) (91 . 0) (10 -2.3921111605 45.1813851190) (40 . 0.0000000000) (41 . 0.0000000000) (42 . 0.0000000000) (91 . 0) (10 -1.8671111605 44.7931565513) (40 . 0.0000000000) (41 . 0.0000000000) (42 . 0.0000000000) (91 . 0) (10 2.5828888395 45.7629549452) (40 . 0.0000000000) (41 . 0.0000000000) (42 . 0.0000000000) (91 . 0) (10 3.1078888395 46.1511835129) (40 . 0.0000000000) (41 . 0.0000000000) (42 . 0.0000000000) (91 . 0) (10 2.5828888395 46.5394120805) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 55.5896136866) (40 . 0.0000000000) (41 . 0.0000000000) (42 . 0.0000000000) (91 . 0) (10 -2.3921111605 55.2013851190) (40 . 0.0000000000) (41 . 0.0000000000) (42 . 0.0000000000) (91 . 0) (10 -1.8671111605 54.8131565513) (40 . 0.0000000000) (41 . 0.0000000000) (42 . 0.0000000000) (91 . 0) (10 2.5828888395 55.7829549452) (40 . 0.0000000000) (41 . 0.0000000000) (42 . 0.0000000000) (91 . 0) (10 3.1078888395 56.1711835129) (40 . 0.0000000000) (41 . 0.0000000000) (42 . 0.0000000000) (91 . 0) (10 2.5828888395 56.5594120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 3.1078888395 47.8211835129 0.0000000000) (11 -2.3921111605 46.8513851190 0.0000000000) (210 0.0000000000 0.0000000000 1.0000000000))
((0 . "LINE") (100 . "AcDbEntity") (67 . 0) (8 . "A-Window") (62 . 151) (6 . "Continuous") (100 . "AcDbLine") (10 3.1078888395 56.1711835129 0.0000000000) (11 -2.3921111605 55.2013851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 47.2396136866) (40 . 0.0000000000) (41 . 0.0000000000) (42 . 0.0000000000) (91 . 0) (10 -2.3921111605 46.8513851190) (40 . 0.0000000000) (41 . 0.0000000000) (42 . 0.0000000000) (91 . 0) (10 -1.8671111605 46.4631565513) (40 . 0.0000000000) (41 . 0.0000000000) (42 . 0.0000000000) (91 . 0) (10 2.5828888395 47.4329549452) (40 . 0.0000000000) (41 . 0.0000000000) (42 . 0.0000000000) (91 . 0) (10 3.1078888395 47.8211835129) (40 . 0.0000000000) (41 . 0.0000000000) (42 . 0.0000000000) (91 . 0) (10 2.5828888395 48.2094120805) (40 . 0.0000000000) (41 . 0.0000000000) (42 . 0.0000000000) (91 . 0) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 57.2596136866) (40 . 0.0000000000) (41 . 0.0000000000) (42 . 0.0000000000) (91 . 0) (10 -2.3921111605 56.8713851190) (40 . 0.0000000000) (41 . 0.0000000000) (42 . 0.0000000000) (91 . 0) (10 -1.8671111605 56.4831565513) (40 . 0.0000000000) (41 . 0.0000000000) (42 . 0.0000000000) (91 . 0) (10 2.5828888395 57.4529549452) (40 . 0.0000000000) (41 . 0.0000000000) (42 . 0.0000000000) (91 . 0) (10 3.1078888395 57.8411835129) (40 . 0.0000000000) (41 . 0.0000000000) (42 . 0.0000000000) (91 . 0) (10 2.5828888395 58.2294120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 3.1078888395 57.8411835129 0.0000000000) (11 -2.3921111605 56.8713851190 0.0000000000) (210 0.0000000000 0.0000000000 1.0000000000))
((0 . "LINE") (100 . "AcDbEntity") (67 . 0) (8 . "A-Window") (62 . 151) (6 . "Continuous") (100 . "AcDbLine") (10 3.1078888395 46.1511835129 0.0000000000) (11 -2.3921111605 45.1813851190 0.0000000000) (210 0.0000000000 0.0000000000 1.0000000000))
((0 . "LWPOLYLINE") (100 . "AcDbEntity") (67 . 0) (8 . "A-Window") (62 . 151) (6 . "Continuous") (100 . "AcDbPolyline") (90 . 10) (70 . 0) (43 . 0.0000000000) (38 . 0.0000000000) (39 . 0.0000000000) (10 2.5828888395 42.6957453328) (40 . 0.0000000000) (41 . 0.0000000000) (42 . 0.0000000000) (91 . 0) (10 2.5828888395 41.0687741511) (40 . 0.0000000000) (41 . 0.0000000000) (42 . 0.0000000000) (91 . 0) (10 0.3578888395 39.2017774718) (40 . 0.0000000000) (41 . 0.0000000000) (42 . 0.0000000000) (91 . 0) (10 -1.8671111605 41.0687741511) (40 . 0.0000000000) (41 . 0.0000000000) (42 . 0.0000000000) (91 . 0) (10 -1.8671111605 43.5797314468) (40 . 0.0000000000) (41 . 0.0000000000) (42 . 0.0000000000) (91 . 0) (10 -2.1783611605 43.8709028725) (40 . 0.0000000000) (41 . 0.0000000000) (42 . 0.0000000000) (91 . 0) (10 -1.8671111605 44.1620742983) (40 . 0.0000000000) (41 . 0.0000000000) (42 . -0.2138820884) (91 . 0) (10 1.7415027540 44.6836330695) (40 . 0.0000000000) (41 . 0.0000000000) (42 . 0.0000000000) (91 . 0) (10 -0.1106380000 39.5949181700) (40 . 0.0000000000) (41 . 0.0000000000) (42 . -0.2315249815) (91 . 0) (10 2.5828888395 41.0687741511) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 2.5828888395 59.8994120805 0.0000000000) (11 2.5828888395 60.7929549452 0.0000000000) (210 0.0000000000 0.0000000000 1.0000000000))
((0 . "LINE") (100 . "AcDbEntity") (67 . 0) (8 . "A-Window") (62 . 151) (6 . "Continuous") (100 . "AcDbLine") (10 2.5828888395 61.5694120805 0.0000000000) (11 2.5828888395 62.4629549452 0.0000000000) (210 0.0000000000 0.0000000000 1.0000000000))
((0 . "LINE") (100 . "AcDbEntity") (67 . 0) (8 . "A-Window") (62 . 151) (6 . "Continuous") (100 . "AcDbLine") (10 2.5828888395 63.2394120805 0.0000000000) (11 2.5828888395 61.1329549452 0.0000000000) (210 0.0000000000 0.0000000000 1.0000000000))
((0 . "LINE") (100 . "AcDbEntity") (67 . 0) (8 . "A-Window") (62 . 151) (6 . "Continuous") (100 . "AcDbLine") (10 -1.8671111605 58.9296136866 0.0000000000) (11 -1.8671111605 59.8231565513 0.0000000000) (210 0.0000000000 0.0000000000 1.0000000000))
((0 . "LINE") (100 . "AcDbEntity") (67 . 0) (8 . "A-Window") (62 . 151) (6 . "Continuous") (100 . "AcDbLine") (10 -1.8671111605 60.5996136866 0.0000000000) (11 -1.8671111605 61.4931565513 0.0000000000) (210 0.0000000000 0.0000000000 1.0000000000))
((0 . "LINE") (100 . "AcDbEntity") (67 . 0) (8 . "A-Window") (62 . 151) (6 . "Continuous") (100 . "AcDbLine") (10 -1.8671111605 62.2696136866 0.0000000000) (11 -1.8671111605 63.1631565513 0.0000000000) (210 0.0000000000 0.0000000000 1.0000000000))
((0 . "LINE") (100 . "AcDbEntity") (67 . 0) (8 . "A-Window") (62 . 151) (6 . "Continuous") (100 . "AcDbLine") (10 3.1078888395 61.1811835129 0.0000000000) (11 -2.3921111605 60.2113851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 60.5996136866) (40 . 0.0000000000) (41 . 0.0000000000) (42 . 0.0000000000) (91 . 0) (10 -2.3921111605 60.2113851190) (40 . 0.0000000000) (41 . 0.0000000000) (42 . 0.0000000000) (91 . 0) (10 -1.8671111605 59.8231565513) (40 . 0.0000000000) (41 . 0.0000000000) (42 . 0.0000000000) (91 . 0) (10 2.5828888395 60.7929549452) (40 . 0.0000000000) (41 . 0.0000000000) (42 . 0.0000000000) (91 . 0) (10 3.1078888395 61.1811835129) (40 . 0.0000000000) (41 . 0.0000000000) (42 . 0.0000000000) (91 . 0) (10 2.5828888395 61.5694120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 3.1078888395 62.8511835129 0.0000000000) (11 -2.3921111605 61.8813851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 62.2696136866) (40 . 0.0000000000) (41 . 0.0000000000) (42 . 0.0000000000) (91 . 0) (10 -2.3921111605 61.8813851190) (40 . 0.0000000000) (41 . 0.0000000000) (42 . 0.0000000000) (91 . 0) (10 -1.8671111605 61.4931565513) (40 . 0.0000000000) (41 . 0.0000000000) (42 . 0.0000000000) (91 . 0) (10 2.5828888395 62.4629549452) (40 . 0.0000000000) (41 . 0.0000000000) (42 . 0.0000000000) (91 . 0) (10 3.1078888395 62.8511835129) (40 . 0.0000000000) (41 . 0.0000000000) (42 . 0.0000000000) (91 . 0) (10 2.5828888395 63.2394120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 3.1078888395 61.5211835128 0.0000000000) (11 -2.3921111605 63.5513851190 0.0000000000) (210 0.0000000000 0.0000000000 1.0000000000))
((0 . "LINE") (100 . "AcDbEntity") (67 . 0) (8 . "A-Window") (62 . 151) (6 . "Continuous") (100 . "AcDbLine") (10 3.1078888395 59.5111835129 0.0000000000) (11 -2.3921111605 58.5413851190 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 58.9296136866) (40 . 0.0000000000) (41 . 0.0000000000) (42 . 0.0000000000) (91 . 0) (10 -2.3921111605 58.5413851190) (40 . 0.0000000000) (41 . 0.0000000000) (42 . 0.0000000000) (91 . 0) (10 -1.8671111605 58.1531565513) (40 . 0.0000000000) (41 . 0.0000000000) (42 . 0.0000000000) (91 . 0) (10 2.5828888395 59.1229549452) (40 . 0.0000000000) (41 . 0.0000000000) (42 . 0.0000000000) (91 . 0) (10 3.1078888395 59.5111835129) (40 . 0.0000000000) (41 . 0.0000000000) (42 . 0.0000000000) (91 . 0) (10 2.5828888395 59.8994120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 2.5828888395 58.2294120805 0.0000000000) (11 2.5828888395 59.1229549452 0.0000000000) (210 0.0000000000 0.0000000000 1.0000000000))
((0 . "LINE") (100 . "AcDbEntity") (67 . 0) (8 . "A-Window") (62 . 151) (6 . "Continuous") (100 . "AcDbLine") (10 2.5828888395 54.8894120805 0.0000000000) (11 2.5828888395 55.7829549452 0.0000000000) (210 0.0000000000 0.0000000000 1.0000000000))
((0 . "LINE") (100 . "AcDbEntity") (67 . 0) (8 . "A-Window") (62 . 151) (6 . "Continuous") (100 . "AcDbLine") (10 -1.8671111605 53.9196136866 0.0000000000) (11 -1.8671111605 54.8131565513 0.0000000000) (210 0.0000000000 0.0000000000 1.0000000000))
((0 . "LINE") (100 . "AcDbEntity") (67 . 0) (8 . "A-Window") (62 . 151) (6 . "Continuous") (100 . "AcDbLine") (10 2.5828888395 54.8894120805 0.0000000000) (11 2.5828888395 55.7829549452 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 53.9196136866) (40 . 0.0000000000) (41 . 0.0000000000) (42 . 0.0000000000) (91 . 0) (10 -2.3921111605 53.5313851190) (40 . 0.0000000000) (41 . 0.0000000000) (42 . 0.0000000000) (91 . 0) (10 -1.8671111605 53.1431565513) (40 . 0.0000000000) (41 . 0.0000000000) (42 . 0.0000000000) (91 . 0) (10 2.5828888395 54.1129549452) (40 . 0.0000000000) (41 . 0.0000000000) (42 . 0.0000000000) (91 . 0) (10 3.1078888395 54.5011835129) (40 . 0.0000000000) (41 . 0.0000000000) (42 . 0.0000000000) (91 . 0) (10 2.5828888395 54.8894120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 3.1078888395 54.5011835129 0.0000000000) (11 -2.3921111605 53.5313851190 0.0000000000) (210 0.0000000000 0.0000000000 1.0000000000))
((0 . "LINE") (100 . "AcDbEntity") (67 . 0) (8 . "A-Window") (62 . 151) (6 . "Continuous") (100 . "AcDbLine") (10 2.5828888395 53.2194120805 0.0000000000) (11 2.5828888395 54.1129549452 0.0000000000) (210 0.0000000000 0.0000000000 1.0000000000))
((0 . "LINE") (100 . "AcDbEntity") (67 . 0) (8 . "A-Window") (62 . 151) (6 . "Continuous") (100 . "AcDbLine") (10 -1.8671111605 52.2496136866 0.0000000000) (11 -1.8671111605 53.1431565513 0.0000000000) (210 0.0000000000 0.0000000000 1.0000000000))
((0 . "LINE") (100 . "AcDbEntity") (67 . 0) (8 . "A-Window") (62 . 151) (6 . "Continuous") (100 . "AcDbLine") (10 2.5828888395 53.2194120805 0.0000000000) (11 2.5828888395 54.1129549452 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 52.2496136866) (40 . 0.0000000000) (41 . 0.0000000000) (42 . 0.0000000000) (91 . 0) (10 -2.3921111605 51.8613851189) (40 . 0.0000000000) (41 . 0.0000000000) (42 . 0.0000000000) (91 . 0) (10 -1.8671111605 51.4731565513) (40 . 0.0000000000) (41 . 0.0000000000) (42 . 0.0000000000) (91 . 0) (10 2.5828888395 52.4429549452) (40 . 0.0000000000) (41 . 0.0000000000) (42 . 0.0000000000) (91 . 0) (10 3.1078888395 52.8311835129) (40 . 0.0000000000) (41 . 0.0000000000) (42 . 0.0000000000) (91 . 0) (10 2.5828888395 53.2194120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 3.1078888395 52.8311835129 0.0000000000) (11 -2.3921111605 51.8613851189 0.0000000000) (210 0.0000000000 0.0000000000 1.0000000000))
((0 . "LINE") (100 . "AcDbEntity") (67 . 0) (8 . "A-Window") (62 . 151) (6 . "Continuous") (100 . "AcDbLine") (10 7.3578888395 71.3967000000 0.0000000000) (11 8.8578888395 71.3967000000 0.0000000000) (210 0.0000000000 0.0000000000 1.0000000000))
((0 . "LINE") (100 . "AcDbEntity") (67 . 0) (8 . "A-Window") (62 . 151) (6 . "Continuous") (100 . "AcDbLine") (10 7.3578888395 72.8917774718 0.0000000000) (11 7.3578888395 71.3967000000 0.0000000000) (210 0.0000000000 0.0000000000 1.0000000000))
((0 . "LINE") (100 . "AcDbEntity") (67 . 0) (8 . "A-Window") (62 . 151) (6 . "Continuous") (100 . "AcDbLine") (10 5.8177271261 72.8917774718 0.0000000000) (11 7.3578888395 72.8917774718 0.0000000000) (210 0.0000000000 0.0000000000 1.0000000000))
((0 . "LINE") (100 . "AcDbEntity") (67 . 0) (8 . "A-Window") (62 . 151) (6 . "Continuous") (100 . "AcDbLine") (10 -6.6421111605 71.3967000000 0.0000000000) (11 -6.6421111605 72.8917774718 0.0000000000) (210 0.0000000000 0.0000000000 1.0000000000))
((0 . "LINE") (100 . "AcDbEntity") (67 . 0) (8 . "A-Window") (62 . 151) (6 . "Continuous") (100 . "AcDbLine") (10 -8.1421111605 71.3967000000 0.0000000000) (11 -6.6421111605 71.3967000000 0.0000000000) (210 0.0000000000 0.0000000000 1.0000000000))
((0 . "LWPOLYLINE") (100 . "AcDbEntity") (67 . 0) (8 . "A-Window") (62 . 151) (6 . "Continuous") (100 . "AcDbPolyline") (90 . 4) (70 . 1) (43 . 0.0000000000) (38 . 0.0000000000) (39 . 0.0000000000) (10 7.3578888395 71.3967000000) (40 . 0.0000000000) (41 . 0.0000000000) (42 . 0.0000000000) (91 . 0) (10 -6.6421111605 71.3967000000) (40 . 0.0000000000) (41 . 0.0000000000) (42 . 0.0000000000) (91 . 0) (10 -6.6421111605 72.8917774718) (40 . 0.0000000000) (41 . 0.0000000000) (42 . 0.0000000000) (91 . 0) (10 7.3578888395 72.8917774718) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 2.5828888395 51.5494120805 0.0000000000) (11 2.5828888395 52.4429549452 0.0000000000) (210 0.0000000000 0.0000000000 1.0000000000))
((0 . "LINE") (100 . "AcDbEntity") (67 . 0) (8 . "A-Window") (62 . 151) (6 . "Continuous") (100 . "AcDbLine") (10 -1.8671111605 50.5796136866 0.0000000000) (11 -1.8671111605 51.4731565513 0.0000000000) (210 0.0000000000 0.0000000000 1.0000000000))
((0 . "LINE") (100 . "AcDbEntity") (67 . 0) (8 . "A-Window") (62 . 151) (6 . "Continuous") (100 . "AcDbLine") (10 2.5828888395 51.5494120805 0.0000000000) (11 2.5828888395 52.4429549452 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 50.5796136866) (40 . 0.0000000000) (41 . 0.0000000000) (42 . 0.0000000000) (91 . 0) (10 -2.3921111605 50.1913851190) (40 . 0.0000000000) (41 . 0.0000000000) (42 . 0.0000000000) (91 . 0) (10 -1.8671111605 49.8031565513) (40 . 0.0000000000) (41 . 0.0000000000) (42 . 0.0000000000) (91 . 0) (10 2.5828888395 50.7729549452) (40 . 0.0000000000) (41 . 0.0000000000) (42 . 0.0000000000) (91 . 0) (10 3.1078888395 51.1611835129) (40 . 0.0000000000) (41 . 0.0000000000) (42 . 0.0000000000) (91 . 0) (10 2.5828888395 51.5494120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 3.1078888395 51.1611835129 0.0000000000) (11 -2.3921111605 50.1913851190 0.0000000000) (210 0.0000000000 0.0000000000 1.0000000000))
((0 . "LINE") (100 . "AcDbEntity") (67 . 0) (8 . "A-Window") (62 . 151) (6 . "Continuous") (100 . "AcDbLine") (10 2.5828888395 49.8794120805 0.0000000000) (11 2.5828888395 50.7729549452 0.0000000000) (210 0.0000000000 0.0000000000 1.0000000000))
((0 . "LINE") (100 . "AcDbEntity") (67 . 0) (8 . "A-Window") (62 . 151) (6 . "Continuous") (100 . "AcDbLine") (10 -1.8671111605 48.9096136866 0.0000000000) (11 -1.8671111605 49.8031565513 0.0000000000) (210 0.0000000000 0.0000000000 1.0000000000))
((0 . "LINE") (100 . "AcDbEntity") (67 . 0) (8 . "A-Window") (62 . 151) (6 . "Continuous") (100 . "AcDbLine") (10 2.5828888395 49.8794120805 0.0000000000) (11 2.5828888395 50.7729549452 0.0000000000) (210 0.0000000000 0.0000000000 1.0000000000))
((0 . "LWPOLYLINE") (100 . "AcDbEntity") (67 . 0) (8 . "A-Window") (62 . 151) (6 . "Continuous") (100 . "AcDbPolyline") (90 . 6) (70 . 1) (43 . 0.0000000000) (38 . 0.0000000000) (39 . 0.0000000000) (10 -1.8671111605 48.9096136866) (40 . 0.0000000000) (41 . 0.0000000000) (42 . 0.0000000000) (91 . 0) (10 -2.3921111605 48.5213851190) (40 . 0.0000000000) (41 . 0.0000000000) (42 . 0.0000000000) (91 . 0) (10 -1.8671111605 48.1331565513) (40 . 0.0000000000) (41 . 0.0000000000) (42 . 0.0000000000) (91 . 0) (10 2.5828888395 49.1029549452) (40 . 0.0000000000) (41 . 0.0000000000) (42 . 0.0000000000) (91 . 0) (10 3.1078888395 49.4911835129) (40 . 0.0000000000) (41 . 0.0000000000) (42 . 0.0000000000) (91 . 0) (10 2.5828888395 49.8794120805) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 3.1078888395 49.4911835129 0.0000000000) (11 -2.3921111605 48.5213851190 0.0000000000) (210 0.0000000000 0.0000000000 1.0000000000))
((0 . "ARC") (100 . "AcDbEntity") (67 . 0) (8 . "A-Window") (62 . 151) (6 . "Continuous") (100 . "AcDbCircle") (10 -42.8123962027 66.7859023315 0.0000000000) (40 . 10.6781898097) (210 0.0000000000 0.0000000000 1.0000000000) (100 . "AcDbArc") (50 . -0.3727943380) (51 . 0.0384802174))
((0 . "LINE") (100 . "AcDbEntity") (67 . 0) (8 . "A-Window") (62 . 151) (6 . "Continuous") (100 . "AcDbLine") (10 32.8578888394 38.1967000000 0.0000000000) (11 32.8578888394 42.8966999996 0.0000000000) (210 0.0000000000 0.0000000000 1.0000000000))
((0 . "LWPOLYLINE") (100 . "AcDbEntity") (67 . 0) (8 . "A-Window") (62 . 3) (6 . "Continuous") (100 . "AcDbPolyline") (90 . 44) (70 . 1) (43 . 0.0000000000) (38 . 0.0000000000) (39 . 0.0000000000) (10 24.3642583620 70.2966877930) (40 . 0.0000000000) (41 . 0.0000000000) (42 . 0.0000000000) (91 . 0) (10 24.3642583620 70.0967122071) (40 . 0.0000000000) (41 . 0.0000000000) (42 . 0.4142225008) (91 . 0) (10 24.7642583619 69.6967000001) (40 . 0.0000000000) (41 . 0.0000000000) (42 . 0.0000000000) (91 . 0) (10 24.9642583619 69.6967000001) (40 . 0.0000000000) (41 . 0.0000000000) (42 . -0.4142135624) (91 . 0) (10 25.5642583619 69.0967000001) (40 . 0.0000000000) (41 . 0.0000000000) (42 . 0.0000000000) (91 . 0) (10 25.5642583619 68.8967000001) (40 . 0.0000000000) (41 . 0.0000000000) (42 . -0.2513806714) (91 . 0) (10 25.2959208409 68.3967000001) (40 . 0.0000000000) (41 . 0.0000000000) (42 . 0.0000000000) (91 . 0) (10 23.5640841373 68.3967000001) (40 . 0.0000000000) (41 . 0.0000000000) (42 . 0.4142135624) (91 . 0) (10 23.0640841373 67.8967000001) (40 . 0.0000000000) (41 . 0.0000000000) (42 . 0.0000000000) (91 . 0) (10 23.0640841373 63.2967000001) (40 . 0.0000000000) (41 . 0.0000000000) (42 . 0.4142135624) (91 . 0) (10 23.5640841373 62.7967000001) (40 . 0.0000000000) (41 . 0.0000000000) (42 . 0.0000000000) (91 . 0) (10 23.7742880933 62.7967000001) (40 . 0.0000000000) (41 . 0.0000000000) (42 . 0.0000000000) (91 . 0) (10 23.9189729887 63.1989988507) (40 . 0.0000000000) (41 . 0.0000000000) (42 . 0.0000000000) (91 . 0) (10 24.2762104017 63.1989988507) (40 . 0.0000000000) (41 . 0.0000000000) (42 . 0.0000000000) (91 . 0) (10 24.4159547600 62.7967000001) (40 . 0.0000000000) (41 . 0.0000000000) (42 . 0.0000000000) (91 . 0) (10 25.0576214266 62.7967000001) (40 . 0.0000000000) (41 . 0.0000000000) (42 . 0.0000000000) (91 . 0) (10 25.2023063220 63.1989988507) (40 . 0.0000000000) (41 . 0.0000000000) (42 . 0.0000000000) (91 . 0) (10 25.5595437350 63.1989988507) (40 . 0.0000000000) (41 . 0.0000000000) (42 . 0.0000000000) (91 . 0) (10 25.6992880933 62.7967000001) (40 . 0.0000000000) (41 . 0.0000000000) (42 . 0.0000000000) (91 . 0) (10 26.3409547600 62.7967000001) (40 . 0.0000000000) (41 . 0.0000000000) (42 . 0.0000000000) (91 . 0) (10 26.4856396554 63.1989988507) (40 . 0.0000000000) (41 . 0.0000000000) (42 . 0.0000000000) (91 . 0) (10 26.8428770684 63.1989988507) (40 . 0.0000000000) (41 . 0.0000000000) (42 . 0.0000000000) (91 . 0) (10 26.9826214266 62.7967000001) (40 . 0.0000000000) (41 . 0.0000000000) (42 . 0.0000000000) (91 . 0) (10 27.6242880933 62.7967000001) (40 . 0.0000000000) (41 . 0.0000000000) (42 . 0.0000000000) (91 . 0) (10 27.7689729887 63.1989988507) (40 . 0.0000000000) (41 . 0.0000000000) (42 . 0.0000000000) (91 . 0) (10 28.1262104017 63.1989988507) (40 . 0.0000000000) (41 . 0.0000000000) (42 . 0.0000000000) (91 . 0) (10 28.2659547600 62.7967000001) (40 . 0.0000000000) (41 . 0.0000000000) (42 . 0.0000000000) (91 . 0) (10 28.9076214266 62.7967000001) (40 . 0.0000000000) (41 . 0.0000000000) (42 . 0.0000000000) (91 . 0) (10 29.0523063220 63.1989988507) (40 . 0.0000000000) (41 . 0.0000000000) (42 . 0.0000000000) (91 . 0) (10 29.4095437350 63.1989988507) (40 . 0.0000000000) (41 . 0.0000000000) (42 . 0.0000000000) (91 . 0) (10 29.5492880933 62.7967000001) (40 . 0.0000000000) (41 . 0.0000000000) (42 . 0.0000000000) (91 . 0) (10 29.7640841372 62.7967000001) (40 . 0.0000000000) (41 . 0.0000000000) (42 . 0.4142135624) (91 . 0) (10 30.2640841372 63.2967000001) (40 . 0.0000000000) (41 . 0.0000000000) (42 . 0.0000000000) (91 . 0) (10 30.2640841372 67.8967000001) (40 . 0.0000000000) (41 . 0.0000000000) (42 . 0.4142135624) (91 . 0) (10 29.7640841372 68.3967000001) (40 . 0.0000000000) (41 . 0.0000000000) (42 . 0.0000000000) (91 . 0) (10 28.0325958828 68.3967000001) (40 . 0.0000000000) (41 . 0.0000000000) (42 . -0.2513806714) (91 . 0) (10 27.7642583619 68.8967000001) (40 . 0.0000000000) (41 . 0.0000000000) (42 . 0.0000000000) (91 . 0) (10 27.7642583619 69.0967000001) (40 . 0.0000000000) (41 . 0.0000000000) (42 . -0.4142135624) (91 . 0) (10 28.3642583619 69.6967000001) (40 . 0.0000000000) (41 . 0.0000000000) (42 . 0.0000000000) (91 . 0) (10 28.5642583619 69.6967000001) (40 . 0.0000000000) (41 . 0.0000000000) (42 . 0.4142135624) (91 . 0) (10 28.9642583619 70.0967000001) (40 . 0.0000000000) (41 . 0.0000000000) (42 . 0.0000000000) (91 . 0) (10 28.9642583619 70.2967000001) (40 . 0.0000000000) (41 . 0.0000000000) (42 . 0.4142135624) (91 . 0) (10 28.5642583619 70.6967000001) (40 . 0.0000000000) (41 . 0.0000000000) (42 . 0.0000000000) (91 . 0) (10 24.7642583619 70.6967000001) (40 . 0.0000000000) (41 . 0.0000000000) (42 . 0.4142225008) (91 . 0) (210 0.0000000000 0.0000000000 1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 28.8190841372 67.3467000001) (40 . 0.0000000000) (41 . 0.0000000000) (42 . 0.0000000000) (91 . 0) (10 28.8190841372 64.2467000001) (40 . 0.0000000000) (41 . 0.0000000000) (42 . 0.0000000000) (91 . 0) (10 27.3190841372 64.2467000001) (40 . 0.0000000000) (41 . 0.0000000000) (42 . 0.0000000000) (91 . 0) (10 27.3190841372 67.3467000001) (40 . 0.0000000000) (41 . 0.0000000000) (42 . 0.0000000000) (91 . 0) (210 0.0000000000 0.0000000000 1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 25.9690841372 67.3467000001) (40 . 0.0000000000) (41 . 0.0000000000) (42 . 0.0000000000) (91 . 0) (10 25.9690841372 64.2467000001) (40 . 0.0000000000) (41 . 0.0000000000) (42 . 0.0000000000) (91 . 0) (10 24.4690841372 64.2467000001) (40 . 0.0000000000) (41 . 0.0000000000) (42 . 0.0000000000) (91 . 0) (10 24.4690841372 67.3467000001) (40 . 0.0000000000) (41 . 0.0000000000) (42 . 0.0000000000) (91 . 0) (210 0.0000000000 0.0000000000 1.0000000000))
((0 . "LINE") (100 . "AcDbEntity") (67 . 0) (8 . "A-Window") (62 . 151) (6 . "Continuous") (100 . "AcDbLine") (10 32.8676567472 62.3966999996 0.0000000000) (11 32.8676567472 67.1967000011 0.0000000000) (210 0.0000000000 0.0000000000 1.0000000000))
((0 . "ARC") (100 . "AcDbEntity") (67 . 0) (8 . "A-Window") (62 . 151) (6 . "Continuous") (100 . "AcDbCircle") (10 -42.8123962027 38.2074976685 0.0000000000) (40 . 10.6781898097) (210 0.0000000000 0.0000000000 1.0000000000) (100 . "AcDbArc") (50 . -0.0384802174) (51 . 0.3727943380))
((0 . "LWPOLYLINE") (100 . "AcDbEntity") (67 . 0) (8 . "A-Window") (62 . 3) (6 . "Continuous") (100 . "AcDbPolyline") (90 . 44) (70 . 1) (43 . 0.0000000000) (38 . 0.0000000000) (39 . 0.0000000000) (10 -24.3693354697 34.6967122070) (40 . 0.0000000000) (41 . 0.0000000000) (42 . 0.0000000000) (91 . 0) (10 -24.3693354697 34.8966877930) (40 . 0.0000000000) (41 . 0.0000000000) (42 . 0.4142225008) (91 . 0) (10 -24.7693354695 35.2967000000) (40 . 0.0000000000) (41 . 0.0000000000) (42 . 0.0000000000) (91 . 0) (10 -24.9693354696 35.2967000000) (40 . 0.0000000000) (41 . 0.0000000000) (42 . -0.4142135624) (91 . 0) (10 -25.5693354696 35.8967000000) (40 . 0.0000000000) (41 . 0.0000000000) (42 . 0.0000000000) (91 . 0) (10 -25.5693354696 36.0967000000) (40 . 0.0000000000) (41 . 0.0000000000) (42 . -0.2513806714) (91 . 0) (10 -25.3009979486 36.5967000000) (40 . 0.0000000000) (41 . 0.0000000000) (42 . 0.0000000000) (91 . 0) (10 -23.5691612449 36.5967000000) (40 . 0.0000000000) (41 . 0.0000000000) (42 . 0.4142135624) (91 . 0) (10 -23.0691612449 37.0967000000) (40 . 0.0000000000) (41 . 0.0000000000) (42 . 0.0000000000) (91 . 0) (10 -23.0691612449 41.6967000000) (40 . 0.0000000000) (41 . 0.0000000000) (42 . 0.4142135624) (91 . 0) (10 -23.5691612449 42.1967000000) (40 . 0.0000000000) (41 . 0.0000000000) (42 . 0.0000000000) (91 . 0) (10 -23.7793652010 42.1967000000) (40 . 0.0000000000) (41 . 0.0000000000) (42 . 0.0000000000) (91 . 0) (10 -23.9240500964 41.7944011494) (40 . 0.0000000000) (41 . 0.0000000000) (42 . 0.0000000000) (91 . 0) (10 -24.2812875094 41.7944011494) (40 . 0.0000000000) (41 . 0.0000000000) (42 . 0.0000000000) (91 . 0) (10 -24.4210318676 42.1967000000) (40 . 0.0000000000) (41 . 0.0000000000) (42 . 0.0000000000) (91 . 0) (10 -25.0626985343 42.1967000000) (40 . 0.0000000000) (41 . 0.0000000000) (42 . 0.0000000000) (91 . 0) (10 -25.2073834297 41.7944011494) (40 . 0.0000000000) (41 . 0.0000000000) (42 . 0.0000000000) (91 . 0) (10 -25.5646208427 41.7944011494) (40 . 0.0000000000) (41 . 0.0000000000) (42 . 0.0000000000) (91 . 0) (10 -25.7043652010 42.1967000000) (40 . 0.0000000000) (41 . 0.0000000000) (42 . 0.0000000000) (91 . 0) (10 -26.3460318676 42.1967000000) (40 . 0.0000000000) (41 . 0.0000000000) (42 . 0.0000000000) (91 . 0) (10 -26.4907167631 41.7944011494) (40 . 0.0000000000) (41 . 0.0000000000) (42 . 0.0000000000) (91 . 0) (10 -26.8479541760 41.7944011494) (40 . 0.0000000000) (41 . 0.0000000000) (42 . 0.0000000000) (91 . 0) (10 -26.9876985343 42.1967000000) (40 . 0.0000000000) (41 . 0.0000000000) (42 . 0.0000000000) (91 . 0) (10 -27.6293652010 42.1967000000) (40 . 0.0000000000) (41 . 0.0000000000) (42 . 0.0000000000) (91 . 0) (10 -27.7740500964 41.7944011494) (40 . 0.0000000000) (41 . 0.0000000000) (42 . 0.0000000000) (91 . 0) (10 -28.1312875094 41.7944011494) (40 . 0.0000000000) (41 . 0.0000000000) (42 . 0.0000000000) (91 . 0) (10 -28.2710318676 42.1967000000) (40 . 0.0000000000) (41 . 0.0000000000) (42 . 0.0000000000) (91 . 0) (10 -28.9126985343 42.1967000000) (40 . 0.0000000000) (41 . 0.0000000000) (42 . 0.0000000000) (91 . 0) (10 -29.0573834297 41.7944011494) (40 . 0.0000000000) (41 . 0.0000000000) (42 . 0.0000000000) (91 . 0) (10 -29.4146208427 41.7944011494) (40 . 0.0000000000) (41 . 0.0000000000) (42 . 0.0000000000) (91 . 0) (10 -29.5543652010 42.1967000000) (40 . 0.0000000000) (41 . 0.0000000000) (42 . 0.0000000000) (91 . 0) (10 -29.7691612449 42.1967000000) (40 . 0.0000000000) (41 . 0.0000000000) (42 . 0.4142135624) (91 . 0) (10 -30.2691612449 41.6967000000) (40 . 0.0000000000) (41 . 0.0000000000) (42 . 0.0000000000) (91 . 0) (10 -30.2691612449 37.0967000000) (40 . 0.0000000000) (41 . 0.0000000000) (42 . 0.4142135624) (91 . 0) (10 -29.7691612449 36.5967000000) (40 . 0.0000000000) (41 . 0.0000000000) (42 . 0.0000000000) (91 . 0) (10 -28.0376729905 36.5967000000) (40 . 0.0000000000) (41 . 0.0000000000) (42 . -0.2513806714) (91 . 0) (10 -27.7693354695 36.0967000000) (40 . 0.0000000000) (41 . 0.0000000000) (42 . 0.0000000000) (91 . 0) (10 -27.7693354695 35.8967000000) (40 . 0.0000000000) (41 . 0.0000000000) (42 . -0.4142135624) (91 . 0) (10 -28.3693354695 35.2967000000) (40 . 0.0000000000) (41 . 0.0000000000) (42 . 0.0000000000) (91 . 0) (10 -28.5693354696 35.2967000000) (40 . 0.0000000000) (41 . 0.0000000000) (42 . 0.4142135624) (91 . 0) (10 -28.9693354696 34.8967000000) (40 . 0.0000000000) (41 . 0.0000000000) (42 . 0.0000000000) (91 . 0) (10 -28.9693354696 34.6967000000) (40 . 0.0000000000) (41 . 0.0000000000) (42 . 0.4142135624) (91 . 0) (10 -28.5693354696 34.2967000000) (40 . 0.0000000000) (41 . 0.0000000000) (42 . 0.0000000000) (91 . 0) (10 -24.7693354695 34.2967000000) (40 . 0.0000000000) (41 . 0.0000000000) (42 . 0.4142225008) (91 . 0) (210 0.0000000000 0.0000000000 1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 -28.8241612449 37.6467000000) (40 . 0.0000000000) (41 . 0.0000000000) (42 . 0.0000000000) (91 . 0) (10 -28.8241612449 40.7467000000) (40 . 0.0000000000) (41 . 0.0000000000) (42 . 0.0000000000) (91 . 0) (10 -27.3241612449 40.7467000000) (40 . 0.0000000000) (41 . 0.0000000000) (42 . 0.0000000000) (91 . 0) (10 -27.3241612449 37.6467000000) (40 . 0.0000000000) (41 . 0.0000000000) (42 . 0.0000000000) (91 . 0) (210 0.0000000000 0.0000000000 1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 -25.9741612449 37.6467000000) (40 . 0.0000000000) (41 . 0.0000000000) (42 . 0.0000000000) (91 . 0) (10 -25.9741612449 40.7467000000) (40 . 0.0000000000) (41 . 0.0000000000) (42 . 0.0000000000) (91 . 0) (10 -24.4741612449 40.7467000000) (40 . 0.0000000000) (41 . 0.0000000000) (42 . 0.0000000000) (91 . 0) (10 -24.4741612449 37.6467000000) (40 . 0.0000000000) (41 . 0.0000000000) (42 . 0.0000000000) (91 . 0) (210 0.0000000000 0.0000000000 1.0000000000))
((0 . "LWPOLYLINE") (100 . "AcDbEntity") (67 . 0) (8 . "A-Window") (62 . 3) (6 . "Continuous") (100 . "AcDbPolyline") (90 . 44) (70 . 1) (43 . 0.0000000000) (38 . 0.0000000000) (39 . 0.0000000000) (10 -25.0851131488 34.6967122070) (40 . 0.0000000000) (41 . 0.0000000000) (42 . 0.0000000000) (91 . 0) (10 -25.0851131488 34.8966877930) (40 . 0.0000000000) (41 . 0.0000000000) (42 . 0.4142225008) (91 . 0) (10 -25.4851131486 35.2967000000) (40 . 0.0000000000) (41 . 0.0000000000) (42 . 0.0000000000) (91 . 0) (10 -25.6851131486 35.2967000000) (40 . 0.0000000000) (41 . 0.0000000000) (42 . -0.4142135624) (91 . 0) (10 -26.2851131486 35.8967000000) (40 . 0.0000000000) (41 . 0.0000000000) (42 . 0.0000000000) (91 . 0) (10 -26.2851131486 36.0967000000) (40 . 0.0000000000) (41 . 0.0000000000) (42 . -0.2513806714) (91 . 0) (10 -26.0167756276 36.5967000000) (40 . 0.0000000000) (41 . 0.0000000000) (42 . 0.0000000000) (91 . 0) (10 -24.2849389240 36.5967000000) (40 . 0.0000000000) (41 . 0.0000000000) (42 . 0.4142135624) (91 . 0) (10 -23.7849389240 37.0967000000) (40 . 0.0000000000) (41 . 0.0000000000) (42 . 0.0000000000) (91 . 0) (10 -23.7849389240 41.6967000000) (40 . 0.0000000000) (41 . 0.0000000000) (42 . 0.4142135624) (91 . 0) (10 -24.2849389240 42.1967000000) (40 . 0.0000000000) (41 . 0.0000000000) (42 . 0.0000000000) (91 . 0) (10 -24.4951428800 42.1967000000) (40 . 0.0000000000) (41 . 0.0000000000) (42 . 0.0000000000) (91 . 0) (10 -24.6398277754 41.7944011494) (40 . 0.0000000000) (41 . 0.0000000000) (42 . 0.0000000000) (91 . 0) (10 -24.9970651884 41.7944011494) (40 . 0.0000000000) (41 . 0.0000000000) (42 . 0.0000000000) (91 . 0) (10 -25.1368095467 42.1967000000) (40 . 0.0000000000) (41 . 0.0000000000) (42 . 0.0000000000) (91 . 0) (10 -25.7784762133 42.1967000000) (40 . 0.0000000000) (41 . 0.0000000000) (42 . 0.0000000000) (91 . 0) (10 -25.9231611088 41.7944011494) (40 . 0.0000000000) (41 . 0.0000000000) (42 . 0.0000000000) (91 . 0) (10 -26.2803985217 41.7944011494) (40 . 0.0000000000) (41 . 0.0000000000) (42 . 0.0000000000) (91 . 0) (10 -26.4201428800 42.1967000000) (40 . 0.0000000000) (41 . 0.0000000000) (42 . 0.0000000000) (91 . 0) (10 -27.0618095467 42.1967000000) (40 . 0.0000000000) (41 . 0.0000000000) (42 . 0.0000000000) (91 . 0) (10 -27.2064944421 41.7944011494) (40 . 0.0000000000) (41 . 0.0000000000) (42 . 0.0000000000) (91 . 0) (10 -27.5637318551 41.7944011494) (40 . 0.0000000000) (41 . 0.0000000000) (42 . 0.0000000000) (91 . 0) (10 -27.7034762133 42.1967000000) (40 . 0.0000000000) (41 . 0.0000000000) (42 . 0.0000000000) (91 . 0) (10 -28.3451428800 42.1967000000) (40 . 0.0000000000) (41 . 0.0000000000) (42 . 0.0000000000) (91 . 0) (10 -28.4898277754 41.7944011494) (40 . 0.0000000000) (41 . 0.0000000000) (42 . 0.0000000000) (91 . 0) (10 -28.8470651884 41.7944011494) (40 . 0.0000000000) (41 . 0.0000000000) (42 . 0.0000000000) (91 . 0) (10 -28.9868095467 42.1967000000) (40 . 0.0000000000) (41 . 0.0000000000) (42 . 0.0000000000) (91 . 0) (10 -29.6284762133 42.1967000000) (40 . 0.0000000000) (41 . 0.0000000000) (42 . 0.0000000000) (91 . 0) (10 -29.7731611088 41.7944011494) (40 . 0.0000000000) (41 . 0.0000000000) (42 . 0.0000000000) (91 . 0) (10 -30.1303985217 41.7944011494) (40 . 0.0000000000) (41 . 0.0000000000) (42 . 0.0000000000) (91 . 0) (10 -30.2701428800 42.1967000000) (40 . 0.0000000000) (41 . 0.0000000000) (42 . 0.0000000000) (91 . 0) (10 -30.4849389239 42.1967000000) (40 . 0.0000000000) (41 . 0.0000000000) (42 . 0.4142135624) (91 . 0) (10 -30.9849389239 41.6967000000) (40 . 0.0000000000) (41 . 0.0000000000) (42 . 0.0000000000) (91 . 0) (10 -30.9849389239 37.0967000000) (40 . 0.0000000000) (41 . 0.0000000000) (42 . 0.4142135624) (91 . 0) (10 -30.4849389239 36.5967000000) (40 . 0.0000000000) (41 . 0.0000000000) (42 . 0.0000000000) (91 . 0) (10 -28.7534506695 36.5967000000) (40 . 0.0000000000) (41 . 0.0000000000) (42 . -0.2513806714) (91 . 0) (10 -28.4851131486 36.0967000000) (40 . 0.0000000000) (41 . 0.0000000000) (42 . 0.0000000000) (91 . 0) (10 -28.4851131486 35.8967000000) (40 . 0.0000000000) (41 . 0.0000000000) (42 . -0.4142135624) (91 . 0) (10 -29.0851131486 35.2967000000) (40 . 0.0000000000) (41 . 0.0000000000) (42 . 0.0000000000) (91 . 0) (10 -29.2851131486 35.2967000000) (40 . 0.0000000000) (41 . 0.0000000000) (42 . 0.4142135624) (91 . 0) (10 -29.6851131486 34.8967000000) (40 . 0.0000000000) (41 . 0.0000000000) (42 . 0.0000000000) (91 . 0) (10 -29.6851131486 34.6967000000) (40 . 0.0000000000) (41 . 0.0000000000) (42 . 0.4142135624) (91 . 0) (10 -29.2851131486 34.2967000000) (40 . 0.0000000000) (41 . 0.0000000000) (42 . 0.0000000000) (91 . 0) (10 -25.4851131486 34.2967000000) (40 . 0.0000000000) (41 . 0.0000000000) (42 . 0.4142225008) (91 . 0) (210 0.0000000000 0.0000000000 -1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 -29.5399389240 37.6467000000) (40 . 0.0000000000) (41 . 0.0000000000) (42 . 0.0000000000) (91 . 0) (10 -29.5399389240 40.7467000000) (40 . 0.0000000000) (41 . 0.0000000000) (42 . 0.0000000000) (91 . 0) (10 -28.0399389240 40.7467000000) (40 . 0.0000000000) (41 . 0.0000000000) (42 . 0.0000000000) (91 . 0) (10 -28.0399389240 37.6467000000) (40 . 0.0000000000) (41 . 0.0000000000) (42 . 0.0000000000) (91 . 0) (210 0.0000000000 0.0000000000 -1.0000000000))
((0 . "LWPOLYLINE") (100 . "AcDbEntity") (67 . 0) (8 . "A-Window") (62 . 3) (6 . "Continuous") (100 . "AcDbPolyline") (90 . 4) (70 . 1) (43 . 0.0000000000) (38 . 0.0000000000) (39 . 0.0000000000) (10 -26.6899389239 37.6467000000) (40 . 0.0000000000) (41 . 0.0000000000) (42 . 0.0000000000) (91 . 0) (10 -26.6899389239 40.7467000000) (40 . 0.0000000000) (41 . 0.0000000000) (42 . 0.0000000000) (91 . 0) (10 -25.1899389239 40.7467000000) (40 . 0.0000000000) (41 . 0.0000000000) (42 . 0.0000000000) (91 . 0) (10 -25.1899389239 37.6467000000) (40 . 0.0000000000) (41 . 0.0000000000) (42 . 0.0000000000) (91 . 0) (210 0.0000000000 0.0000000000 -1.0000000000))
((0 . "LWPOLYLINE") (100 . "AcDbEntity") (67 . 0) (8 . "A-Window") (62 . 3) (6 . "Continuous") (100 . "AcDbPolyline") (90 . 41) (70 . 1) (43 . 0.0000000000) (38 . 0.0000000000) (39 . 0.0000000000) (10 -1640.4056645312 64.4075135888) (40 . 0.0000000000) (41 . 0.0000000000) (42 . 0.0000000000) (91 . 0) (10 -1641.2556645312 64.4075135888) (40 . 0.0000000000) (41 . 0.0000000000) (42 . 0.4142135624) (91 . 0) (10 -1641.7556645312 63.9075135888) (40 . 0.0000000000) (41 . 0.0000000000) (42 . 0.0000000000) (91 . 0) (10 -1641.7556645312 62.9075135888) (40 . 0.0000000000) (41 . 0.0000000000) (42 . -0.4142135624) (91 . 0) (10 -1642.2556645312 62.4075135888) (40 . 0.0000000000) (41 . 0.0000000000) (42 . 0.0000000000) (91 . 0) (10 -1643.6056645312 62.4075135888) (40 . 0.0000000000) (41 . 0.0000000000) (42 . 0.4142135624) (91 . 0) (10 -1644.1056645312 61.9075135888) (40 . 0.0000000000) (41 . 0.0000000000) (42 . 0.0000000000) (91 . 0) (10 -1644.1056645312 61.7075135888) (40 . 0.0000000000) (41 . 0.0000000000) (42 . 0.4142135624) (91 . 0) (10 -1643.6056645312 61.2075135888) (40 . 0.0000000000) (41 . 0.0000000000) (42 . 0.0000000000) (91 . 0) (10 -1641.3556645312 61.2075135888) (40 . 0.0000000000) (41 . 0.0000000000) (42 . 0.0000000000) (91 . 0) (10 -1639.4056645313 61.2075135888) (40 . 0.0000000000) (41 . 0.0000000000) (42 . -0.4142135624) (91 . 0) (10 -1638.9056645313 60.7075135888) (40 . 0.0000000000) (41 . 0.0000000000) (42 . 0.0000000000) (91 . 0) (10 -1638.9056645313 45.4944011494) (40 . 0.0000000000) (41 . 0.0000000000) (42 . -0.4142135624) (91 . 0) (10 -1639.4056645313 44.9944011494) (40 . 0.0000000000) (41 . 0.0000000000) (42 . 0.0000000000) (91 . 0) (10 -1643.6056645312 44.9944011494) (40 . 0.0000000000) (41 . 0.0000000000) (42 . 0.4142135624) (91 . 0) (10 -1644.1056645312 44.4944011494) (40 . 0.0000000000) (41 . 0.0000000000) (42 . 0.0000000000) (91 . 0) (10 -1644.1056645312 44.2944011494) (40 . 0.0000000000) (41 . 0.0000000000) (42 . 0.4142135624) (91 . 0) (10 -1643.6056645312 43.7944011494) (40 . 0.0000000000) (41 . 0.0000000000) (42 . 0.0000000000) (91 . 0) (10 -1642.2556645312 43.7944011494) (40 . 0.0000000000) (41 . 0.0000000000) (42 . -0.4142135624) (91 . 0) (10 -1641.7556645312 43.2944011494) (40 . 0.0000000000) (41 . 0.0000000000) (42 . 0.0000000000) (91 . 0) (10 -1641.7556645312 42.2944011494) (40 . 0.0000000000) (41 . 0.0000000000) (42 . 0.4142135624) (91 . 0) (10 -1641.2556645312 41.7944011494) (40 . 0.0000000000) (41 . 0.0000000000) (42 . 0.0000000000) (91 . 0) (10 -1640.4056645313 41.7944011494) (40 . 0.0000000000) (41 . 0.0000000000) (42 . 0.4142135624) (91 . 0) (10 -1639.9056645313 42.2944011494) (40 . 0.0000000000) (41 . 0.0000000000) (42 . 0.0000000000) (91 . 0) (10 -1639.9056645313 43.2944011494) (40 . 0.0000000000) (41 . 0.0000000000) (42 . -0.4142135624) (91 . 0) (10 -1639.4056645313 43.7944011494) (40 . 0.0000000000) (41 . 0.0000000000) (42 . 0.0000000000) (91 . 0) (10 -1637.9056645313 43.7944011494) (40 . 0.0000000000) (41 . 0.0000000000) (42 . 0.4142135624) (91 . 0) (10 -1637.4056645313 44.2944011494) (40 . 0.0000000000) (41 . 0.0000000000) (42 . 0.0000000000) (91 . 0) (10 -1637.4056645313 46.7944011494) (40 . 0.0000000000) (41 . 0.0000000000) (42 . -0.4142135624) (91 . 0) (10 -1636.9056645313 47.2944011494) (40 . 0.0000000000) (41 . 0.0000000000) (42 . 0.0000000000) (91 . 0) (10 -1635.9056645313 47.2944011494) (40 . 0.0000000000) (41 . 0.0000000000) (42 . 0.4142135624) (91 . 0) (10 -1635.4056645313 47.7944011494) (40 . 0.0000000000) (41 . 0.0000000000) (42 . 0.0000000000) (91 . 0) (10 -1635.4056645313 58.4075135888) (40 . 0.0000000000) (41 . 0.0000000000) (42 . 0.4142135624) (91 . 0) (10 -1635.9056645313 58.9075135888) (40 . 0.0000000000) (41 . 0.0000000000) (42 . 0.0000000000) (91 . 0) (10 -1636.9056645313 58.9075135888) (40 . 0.0000000000) (41 . 0.0000000000) (42 . -0.4142135624) (91 . 0) (10 -1637.4056645313 59.4075135888) (40 . 0.0000000000) (41 . 0.0000000000) (42 . 0.0000000000) (91 . 0) (10 -1637.4056645313 61.9075135888) (40 . 0.0000000000) (41 . 0.0000000000) (42 . 0.4142135624) (91 . 0) (10 -1637.9056645313 62.4075135888) (40 . 0.0000000000) (41 . 0.0000000000) (42 . 0.0000000000) (91 . 0) (10 -1639.4056645313 62.4075135888) (40 . 0.0000000000) (41 . 0.0000000000) (42 . -0.4142135624) (91 . 0) (10 -1639.9056645313 62.9075135888) (40 . 0.0000000000) (41 . 0.0000000000) (42 . 0.0000000000) (91 . 0) (10 -1639.9056645312 63.9075135888) (40 . 0.0000000000) (41 . 0.0000000000) (42 . 0.4142135624) (91 . 0) (210 0.0000000000 0.0000000000 -1.0000000000))
((0 . "LWPOLYLINE") (100 . "AcDbEntity") (67 . 0) (8 . "A-Window") (62 . 3) (6 . "Continuous") (100 . "AcDbPolyline") (90 . 2) (70 . 0) (43 . 0.0000000000) (38 . 0.0000000000) (39 . 0.0000000000) (10 -1635.3578888406 69.1557800149) (40 . 0.0000000000) (41 . 0.0000000000) (42 . 0.0000000000) (91 . 0) (10 -1635.3578888402 33.1842064594) (40 . 0.0000000000) (41 . 0.0000000000) (42 . 0.0000000000) (91 . 0) (210 0.0000000000 0.0000000000 -1.0000000000))
((0 . "LWPOLYLINE") (100 . "AcDbEntity") (67 . 0) (8 . "A-Window") (62 . 3) (6 . "Continuous") (100 . "AcDbPolyline") (90 . 41) (70 . 1) (43 . 0.0000000000) (38 . 0.0000000000) (39 . 0.0000000000) (10 -27.8101131484 64.4075135888) (40 . 0.0000000000) (41 . 0.0000000000) (42 . 0.0000000000) (91 . 0) (10 -26.9601131484 64.4075135888) (40 . 0.0000000000) (41 . 0.0000000000) (42 . -0.4142135624) (91 . 0) (10 -26.4601131484 63.9075135888) (40 . 0.0000000000) (41 . 0.0000000000) (42 . 0.0000000000) (91 . 0) (10 -26.4601131484 62.9075135888) (40 . 0.0000000000) (41 . 0.0000000000) (42 . 0.4142135624) (91 . 0) (10 -25.9601131484 62.4075135888) (40 . 0.0000000000) (41 . 0.0000000000) (42 . 0.0000000000) (91 . 0) (10 -24.6101131484 62.4075135888) (40 . 0.0000000000) (41 . 0.0000000000) (42 . -0.4142135624) (91 . 0) (10 -24.1101131484 61.9075135888) (40 . 0.0000000000) (41 . 0.0000000000) (42 . 0.0000000000) (91 . 0) (10 -24.1101131484 61.7075135888) (40 . 0.0000000000) (41 . 0.0000000000) (42 . -0.4142135624) (91 . 0) (10 -24.6101131484 61.2075135888) (40 . 0.0000000000) (41 . 0.0000000000) (42 . 0.0000000000) (91 . 0) (10 -26.8601131484 61.2075135888) (40 . 0.0000000000) (41 . 0.0000000000) (42 . 0.0000000000) (91 . 0) (10 -28.8101131484 61.2075135888) (40 . 0.0000000000) (41 . 0.0000000000) (42 . 0.4142135624) (91 . 0) (10 -29.3101131484 60.7075135888) (40 . 0.0000000000) (41 . 0.0000000000) (42 . 0.0000000000) (91 . 0) (10 -29.3101131484 45.4944011494) (40 . 0.0000000000) (41 . 0.0000000000) (42 . 0.4142135624) (91 . 0) (10 -28.8101131483 44.9944011494) (40 . 0.0000000000) (41 . 0.0000000000) (42 . 0.0000000000) (91 . 0) (10 -24.6101131484 44.9944011494) (40 . 0.0000000000) (41 . 0.0000000000) (42 . -0.4142135624) (91 . 0) (10 -24.1101131484 44.4944011494) (40 . 0.0000000000) (41 . 0.0000000000) (42 . 0.0000000000) (91 . 0) (10 -24.1101131484 44.2944011494) (40 . 0.0000000000) (41 . 0.0000000000) (42 . -0.4142135624) (91 . 0) (10 -24.6101131484 43.7944011494) (40 . 0.0000000000) (41 . 0.0000000000) (42 . 0.0000000000) (91 . 0) (10 -25.9601131484 43.7944011494) (40 . 0.0000000000) (41 . 0.0000000000) (42 . 0.4142135624) (91 . 0) (10 -26.4601131484 43.2944011494) (40 . 0.0000000000) (41 . 0.0000000000) (42 . 0.0000000000) (91 . 0) (10 -26.4601131484 42.2944011494) (40 . 0.0000000000) (41 . 0.0000000000) (42 . -0.4142135624) (91 . 0) (10 -26.9601131484 41.7944011494) (40 . 0.0000000000) (41 . 0.0000000000) (42 . 0.0000000000) (91 . 0) (10 -27.8101131484 41.7944011494) (40 . 0.0000000000) (41 . 0.0000000000) (42 . -0.4142135624) (91 . 0) (10 -28.3101131484 42.2944011494) (40 . 0.0000000000) (41 . 0.0000000000) (42 . 0.0000000000) (91 . 0) (10 -28.3101131484 43.2944011494) (40 . 0.0000000000) (41 . 0.0000000000) (42 . 0.4142135624) (91 . 0) (10 -28.8101131484 43.7944011494) (40 . 0.0000000000) (41 . 0.0000000000) (42 . 0.0000000000) (91 . 0) (10 -30.3101131484 43.7944011494) (40 . 0.0000000000) (41 . 0.0000000000) (42 . -0.4142135624) (91 . 0) (10 -30.8101131484 44.2944011494) (40 . 0.0000000000) (41 . 0.0000000000) (42 . 0.0000000000) (91 . 0) (10 -30.8101131483 46.7944011494) (40 . 0.0000000000) (41 . 0.0000000000) (42 . 0.4142135624) (91 . 0) (10 -31.3101131483 47.2944011494) (40 . 0.0000000000) (41 . 0.0000000000) (42 . 0.0000000000) (91 . 0) (10 -32.3101131483 47.2944011494) (40 . 0.0000000000) (41 . 0.0000000000) (42 . -0.4142135624) (91 . 0) (10 -32.8101131483 47.7944011494) (40 . 0.0000000000) (41 . 0.0000000000) (42 . 0.0000000000) (91 . 0) (10 -32.8101131483 58.4075135888) (40 . 0.0000000000) (41 . 0.0000000000) (42 . -0.4142135624) (91 . 0) (10 -32.3101131483 58.9075135888) (40 . 0.0000000000) (41 . 0.0000000000) (42 . 0.0000000000) (91 . 0) (10 -31.3101131484 58.9075135888) (40 . 0.0000000000) (41 . 0.0000000000) (42 . 0.4142135624) (91 . 0) (10 -30.8101131484 59.4075135888) (40 . 0.0000000000) (41 . 0.0000000000) (42 . 0.0000000000) (91 . 0) (10 -30.8101131484 61.9075135888) (40 . 0.0000000000) (41 . 0.0000000000) (42 . -0.4142135624) (91 . 0) (10 -30.3101131484 62.4075135888) (40 . 0.0000000000) (41 . 0.0000000000) (42 . 0.0000000000) (91 . 0) (10 -28.8101131484 62.4075135888) (40 . 0.0000000000) (41 . 0.0000000000) (42 . 0.4142135624) (91 . 0) (10 -28.3101131484 62.9075135888) (40 . 0.0000000000) (41 . 0.0000000000) (42 . 0.0000000000) (91 . 0) (10 -28.3101131484 63.9075135888) (40 . 0.0000000000) (41 . 0.0000000000) (42 . -0.4142135624) (91 . 0) (210 0.0000000000 0.0000000000 -1.0000000000))
((0 . "LWPOLYLINE") (100 . "AcDbEntity") (67 . 0) (8 . "A-Window") (62 . 3) (6 . "Continuous") (100 . "AcDbPolyline") (90 . 2) (70 . 0) (43 . 0.0000000000) (38 . 0.0000000000) (39 . 0.0000000000) (10 -32.8578888390 69.1557800149) (40 . 0.0000000000) (41 . 0.0000000000) (42 . 0.0000000000) (91 . 0) (10 -32.8578888394 33.1842064594) (40 . 0.0000000000) (41 . 0.0000000000) (42 . 0.0000000000) (91 . 0) (210 0.0000000000 0.0000000000 -1.0000000000))
)
))
(setq vk:dl-ltype '(
((0 . "LTYPE") (100 . "AcDbSymbolTableRecord") (100 . "AcDbLinetypeTableRecord") (2 . "CENTER") (70 . 0) (3 . "Center ____ _ ____ _ ____ _ ____ _ ____ _ ____") (72 . 65) (73 . 4) (40 . 5.0800000000) (49 . 3.1750000000) (74 . 0) (49 . -0.6350000000) (74 . 0) (49 . 0.6350000000) (74 . 0) (49 . -0.6350000000) (74 . 0))
((0 . "LTYPE") (100 . "AcDbSymbolTableRecord") (100 . "AcDbLinetypeTableRecord") (2 . "HIDDEN") (70 . 0) (3 . "__ __ __ __ __ __ __ __ __ __ __ __ __ __ __ __") (72 . 65) (73 . 2) (40 . 0.3750000000) (49 . 0.2500000000) (74 . 0) (49 . -0.1250000000) (74 . 0))
((0 . "LTYPE") (100 . "AcDbSymbolTableRecord") (100 . "AcDbLinetypeTableRecord") (2 . "CENTER2") (70 . 0) (3 . "Center (.5x) ____ _ ____ _ ____ _ ____ _ ____") (72 . 65) (73 . 4) (40 . 2.5400000000) (49 . 1.5870000000) (74 . 0) (49 . -0.3180000000) (74 . 0) (49 . 0.3180000000) (74 . 0) (49 . -0.3180000000) (74 . 0))
))
(setq vk:dl-layer '((0 . "LAYER") (100 . "AcDbSymbolTableRecord") (100 . "AcDbLayerTableRecord") (2 . "A-Window") (70 . 0) (62 . 151) (6 . "Continuous") (290 . 1) (370 . -3)))
(setq vk:dl-style '((0 . "STYLE") (100 . "AcDbSymbolTableRecord") (100 . "AcDbTextStyleTableRecord") (2 . "Arch-Dim") (70 . 0) (40 . 0.0000000000) (41 . 0.7500000000) (50 . 0.0000000000) (71 . 0) (42 . 0.2000000000) (3 . "romans.shx") (4 . "")))
(setq vk:dl-dimvar '(
("DIMADEC" . 2)
("DIMALT" . 0)
("DIMALTD" . 3)
("DIMALTF" . 0.0393700787)
("DIMALTRND" . 0.0000000000)
("DIMALTTD" . 3)
("DIMALTTZ" . 0)
("DIMALTU" . 2)
("DIMALTZ" . 0)
("DIMAPOST" . "")
("DIMASZ" . 110.0000000000)
("DIMATFIT" . 3)
("DIMAUNIT" . 0)
("DIMAZIN" . 3)
("DIMBLK" . "ArchTick")
("DIMBLK1" . "")
("DIMBLK2" . "")
("DIMCEN" . 150.0000000000)
("DIMCLRD" . 256)
("DIMCLRE" . 256)
("DIMCLRT" . 6)
("DIMDEC" . 0)
("DIMDLE" . 66.0000000000)
("DIMDLI" . 660.0000000000)
("DIMDSEP" . ",")
("DIMEXE" . 66.0000000000)
("DIMEXO" . 0.0000000000)
("DIMFRAC" . 0)
("DIMFXL" . 2.5000000000)
("DIMFXLON" . 0)
("DIMGAP" . 55.0000000000)
("DIMJOGANG" . 0.7853981634)
("DIMJUST" . 0)
("DIMLDRBLK" . "")
("DIMLFAC" . 1.0000000000)
("DIMLIM" . 0)
("DIMLUNIT" . 2)
("DIMLWD" . -2)
("DIMLWE" . -2)
("DIMPOST" . "")
("DIMRND" . 0.0000000000)
("DIMSAH" . 0)
("DIMSCALE" . 0.2500000000)
("DIMSD1" . 0)
("DIMSD2" . 0)
("DIMSE1" . 0)
("DIMSE2" . 0)
("DIMSOXD" . 0)
("DIMTAD" . 1)
("DIMTDEC" . 0)
("DIMTFAC" . 1.0000000000)
("DIMTFILL" . 0)
("DIMTFILLCLR" . 0)
("DIMTIH" . 0)
("DIMTIX" . 1)
("DIMTM" . 0.0000000000)
("DIMTMOVE" . 2)
("DIMTOFL" . 1)
("DIMTOH" . 0)
("DIMTOL" . 0)
("DIMTOLJ" . 0)
("DIMTP" . 0.0000000000)
("DIMTSZ" . 0.0000000000)
("DIMTVP" . 0.8333330000)
("DIMTXSTY" . "Arch-Dim")
("DIMTXT" . 220.0000000000)
("DIMTZIN" . 8)
("DIMUPT" . 0)
("DIMZIN" . 8)
("DIMARCSYM" . 0)
("DIMTXTDIRECTION" . 0)
))
(princ)
